FME workspace 3 Coastal.fmw

Parameters:
- DestDataset_POSTGIS = Dev   # Connection
- SourceDataset_S57 = G:\LDS_vector_20210919\3 Coastal\*.000   # Source S-57 (ENC) Hydrographic Data File(s)

Readers:
- S57_1: S57 from $(SourceDataset_S57)

Writers:
- POSTGIS_1: POSTGIS to $(DestDataset_POSTGIS)

DSID (reader S57_1)
    attributes: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
Generic (reader S57_1)
    attributes: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
SISTAT (reader S57_1)
    attributes: RCID integer, PRIM integer16, GRUP integer16, OBJL integer, RVER integer16, AGEN integer, FIDN integer, FIDS integer, LNAM char(16), LNAM_REFS{} char(16), FFPT_RIND{} integer16, CATSIT char(254), COMCHA char(254), DATEND char(254), DATSTA char(254), NOBJNM char(254), OBJNAM char(254), PEREND char(254), PERSTA char(254), STATUS char(254), INFORM char(254), NINFOM char(254), NTXTDS char(254), SCAMAX integer, SCAMIN integer, TXTDSC char(254), RECDAT char(254), RECIND char(254), SORDAT char(254), SORIND char(254)
    -> AttributeManager_72
AttributeManager_72
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_sistat_point (writer POSTGIS_1)
3_coastal_sistat_point (writer POSTGIS_1)
    attributes: fidn varchar(20), catsit varchar(80), comcha varchar(80), datend varchar(80), datsta varchar(80), nobjnm varchar(80), objnam varchar(80), perend varchar(80), persta varchar(80), status varchar(80), inform varchar(254), ninfom varchar(80), ntxtds varchar(80), scamin numeric(24,15), txtdsc varchar(80), sordat varchar(80), sorind varchar(80)
SLCONS (reader S57_1)
    attributes: RCID integer, PRIM integer16, GRUP integer16, OBJL integer, RVER integer16, AGEN integer, FIDN integer, FIDS integer, LNAM char(16), LNAM_REFS{} char(16), FFPT_RIND{} integer16, CATSLC integer, COLOUR char(254), COLPAT char(254), CONDTN integer, CONRAD integer, CONVIS integer, DATEND char(254), DATSTA char(254), HEIGHT double, HORACC double, HORCLR double, HORLEN double, HORWID double, NATCON char(254), NOBJNM char(254), OBJNAM char(254), STATUS char(254), VERACC double, VERDAT integer,
      VERLEN double, WATLEV integer, INFORM char(254), NINFOM char(254), NTXTDS char(254), SCAMAX integer, SCAMIN integer, TXTDSC char(254), RECDAT char(254), RECIND char(254), SORDAT char(254), SORIND char(254)
    -> AttributeManager_37
AttributeManager_37
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_21
GeometryFilter_21
    BREAK_AGG = No
    GEOM_PORT_NAMES = Point Area Line
    POINT -> 3_coastal_slcons_point (writer POSTGIS_1)
    AREA -> 3_coastal_slcons_polygon (writer POSTGIS_1)
    LINE -> 3_coastal_slcons_arc (writer POSTGIS_1)
3_coastal_slcons_point (writer POSTGIS_1)
    attributes: fidn varchar(20), catslc varchar(80), colour varchar(80), colpat varchar(80), condtn varchar(80), conrad varchar(80), convis varchar(80), datend varchar(80), datsta varchar(80), height numeric(24,15), horacc numeric(24,15), horclr numeric(24,15), horlen numeric(24,15), horwid numeric(24,15), natcon varchar(80), nobjnm varchar(80), objnam varchar(80), status varchar(80), veracc numeric(24,15), verdat varchar(80), verlen numeric(24,15), watlev varchar(80), inform varchar(80), ninfom varchar(80), ntxtds varchar(80), scamin numeric(24,15), txtdsc varchar(80), sordat varchar(80), sorind varchar(80)
3_coastal_slcons_polygon (writer POSTGIS_1)
    attributes: fidn varchar(20), catslc varchar(80), colour varchar(80), colpat varchar(80), condtn varchar(80), conrad varchar(80), convis varchar(80), datend varchar(80), datsta varchar(80), height numeric(24,15), horacc numeric(24,15), horclr numeric(24,15), horlen numeric(24,15), horwid numeric(24,15), natcon varchar(80), nobjnm varchar(80), objnam varchar(80), status varchar(80), veracc numeric(24,15), verdat varchar(80), verlen numeric(24,15), watlev varchar(80), inform varchar(80), ninfom varchar(80), ntxtds varchar(80), scamin numeric(24,15), txtdsc varchar(80), sordat varchar(80), sorind varchar(80)
3_coastal_slcons_arc (writer POSTGIS_1)
    attributes: fidn varchar(20), catslc varchar(80), colour varchar(80), colpat varchar(80), condtn varchar(80), conrad varchar(80), convis varchar(80), datend varchar(80), datsta varchar(80), height numeric(24,15), horacc numeric(24,15), horclr numeric(24,15), horlen numeric(24,15), horwid numeric(24,15), natcon varchar(80), nobjnm varchar(80), objnam varchar(80), status varchar(80), veracc numeric(24,15), verdat varchar(80), verlen numeric(24,15), watlev varchar(20), inform varchar(254), ninfom varchar(80), ntxtds varchar(80), scamin numeric(24,15), txtdsc varchar(80), sordat varchar(80), sorind varchar(80)
SLOGRD (reader S57_1)
    attributes: RCID integer, PRIM integer16, GRUP integer16, OBJL integer, RVER integer16, AGEN integer, FIDN integer, FIDS integer, LNAM char(16), LNAM_REFS{} char(16), FFPT_RIND{} integer16, CATSLO integer, COLOUR char(254), CONRAD integer, CONVIS integer, NATCON char(254), NATQUA char(254), NATSUR char(254), NOBJNM char(254), OBJNAM char(254), INFORM char(254), NINFOM char(254), NTXTDS char(254), SCAMAX integer, SCAMIN integer, TXTDSC char(254), RECDAT char(254), RECIND char(254), SORDAT char(254), SORIND char(254)
    -> AttributeManager_73
AttributeManager_73
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_slogrd_point (writer POSTGIS_1)
3_coastal_slogrd_point (writer POSTGIS_1)
    attributes: fidn varchar(20), catslo varchar(80), colour varchar(80), conrad varchar(80), convis varchar(80), natcon varchar(80), natqua varchar(80), natsur varchar(80), nobjnm varchar(80), objnam varchar(80), inform varchar(80), ninfom varchar(80), ntxtds varchar(80), scamin numeric(24,15), txtdsc varchar(80), sordat varchar(80), sorind varchar(80)
SLOTOP (reader S57_1)
    attributes: RCID integer, PRIM integer16, GRUP integer16, OBJL integer, RVER integer16, AGEN integer, FIDN integer, FIDS integer, LNAM char(16), LNAM_REFS{} char(16), FFPT_RIND{} integer16, CATSLO integer, COLOUR char(254), CONRAD integer, CONVIS integer, ELEVAT double, NATCON char(254), NATQUA char(254), NATSUR char(254), NOBJNM char(254), OBJNAM char(254), VERACC double, VERDAT integer, INFORM char(254), NINFOM char(254), NTXTDS char(254), SCAMAX integer, SCAMIN integer, TXTDSC char(254), RECDAT char(254),
      RECIND char(254), SORDAT char(254), SORIND char(254)
    -> AttributeManager_74
AttributeManager_74
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_slotop_arc (writer POSTGIS_1)
3_coastal_slotop_arc (writer POSTGIS_1)
    attributes: fidn varchar(20), catslo varchar(80), colour varchar(80), conrad varchar(80), convis varchar(80), elevat numeric(24,15), natcon varchar(80), natqua varchar(80), natsur varchar(80), nobjnm varchar(80), objnam varchar(80), veracc numeric(24,15), verdat varchar(80), inform varchar(80), ninfom varchar(80), ntxtds varchar(80), scamin numeric(24,15), txtdsc varchar(80), sordat varchar(80), sorind varchar(80)
SOUNDG (reader S57_1)
    attributes: RCID integer, PRIM integer16, GRUP integer16, OBJL integer, RVER integer16, AGEN integer, FIDN integer, FIDS integer, LNAM char(16), LNAM_REFS{} char(16), FFPT_RIND{} integer16, EXPSOU integer, NOBJNM char(254), OBJNAM char(254), QUASOU char(254), SOUACC double, TECSOU char(254), VERDAT integer, STATUS char(254), INFORM char(254), NINFOM char(254), NTXTDS char(254), SCAMAX integer, SCAMIN integer, TXTDSC char(254), RECDAT char(254), RECIND char(254), SORDAT char(254), SORIND char(254)
    -> AttributeManager_21
AttributeManager_21
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_soundg_point (writer POSTGIS_1)
3_coastal_soundg_point (writer POSTGIS_1)
    attributes: fidn varchar(20), expsou varchar(80), nobjnm varchar(80), objnam varchar(80), quasou varchar(80), souacc numeric(24,15), tecsou varchar(80), verdat varchar(80), status varchar(80), inform varchar(80), ninfom varchar(80), ntxtds varchar(80), scamin numeric(24,15), txtdsc varchar(80), sordat varchar(80), sorind varchar(80)
SPRING (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), INFORM char(254), NINFOM char(254), NTXTDS char(254), SCAMAX integer, SCAMIN integer, TXTDSC char(254), RECDAT char(254), RECIND char(254), SORDAT char(254), SORIND char(254)
    -> AttributeManager_38
AttributeManager_38
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_spring_point (writer POSTGIS_1)
3_coastal_spring_point (writer POSTGIS_1)
    attributes: fidn varchar(20), nobjnm varchar(80), objnam varchar(80), inform varchar(80), ninfom varchar(80), ntxtds varchar(80), scamin numeric(24,15), txtdsc varchar(80), sordat varchar(80), sorind varchar(80)
TESARE (reader S57_1)
    attributes: RCID integer, PRIM integer16, GRUP integer16, OBJL integer, RVER integer16, AGEN integer, FIDN integer, FIDS integer, LNAM char(16), LNAM_REFS{} char(16), FFPT_RIND{} integer16, NATION char(254), RESTRN char(254), INFORM char(254), NINFOM char(254), NTXTDS char(254), SCAMAX integer, SCAMIN integer, TXTDSC char(254), RECDAT char(254), RECIND char(254), SORDAT char(254), SORIND char(254)
    -> AttributeManager_39
AttributeManager_39
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_tesare_polygon (writer POSTGIS_1)
3_coastal_tesare_polygon (writer POSTGIS_1)
    attributes: fidn varchar(20), nation varchar(80), restrn varchar(80), inform varchar(80), ninfom varchar(80), ntxtds varchar(80), scamin numeric(24,15), txtdsc varchar(80), sordat varchar(80), sorind varchar(80)
TIDEWY (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), INFORM char(254), NINFOM char(254), NTXTDS char(254), SCAMAX integer, SCAMIN integer, TXTDSC char(254), RECDAT char(254), RECIND char(254), SORDAT char(254), SORIND char(254)
    -> AttributeManager_75
AttributeManager_75
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE DSNM
    -> 3_coastal_tidewy_arc (writer POSTGIS_1)
3_coastal_tidewy_arc (writer POSTGIS_1)
    attributes: fidn varchar(20), nobjnm varchar(80), objnam varchar(80), inform varchar(80), ninfom varchar(80), ntxtds varchar(80), scamin numeric(24,15), txtdsc varchar(80), recdat varchar(80), recind varchar(80), sordat varchar(80), sorind varchar(80)
TOPMAR (reader S57_1)
    attributes: RCID integer, PRIM integer16, GRUP integer16, OBJL integer, RVER integer16, AGEN integer, FIDN integer, FIDS integer, LNAM char(16), LNAM_REFS{} char(16), FFPT_RIND{} integer16, COLOUR char(254), COLPAT char(254), DATEND char(254), DATSTA char(254), HEIGHT double, MARSYS integer, STATUS char(254), TOPSHP integer, VERACC double, VERDAT integer, VERLEN double, INFORM char(254), NINFOM char(254), NTXTDS char(254), PICREP char(254), SCAMAX integer, SCAMIN integer, TXTDSC char(254), RECDAT char(254),
      RECIND char(254), SORDAT char(254), SORIND char(254)
    -> AttributeManager_40
AttributeManager_40
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_topmar_point (writer POSTGIS_1)
3_coastal_topmar_point (writer POSTGIS_1)
    attributes: fidn varchar(20), colour varchar(80), colpat varchar(80), datend varchar(80), datsta varchar(80), height numeric(24,15), marsys varchar(80), status varchar(80), topshp varchar(80), veracc numeric(24,15), verdat varchar(80), verlen numeric(24,15), inform varchar(80), ninfom varchar(80), ntxtds varchar(80), picrep varchar(80), scamin numeric(24,15), txtdsc varchar(80), sordat varchar(80), sorind varchar(80)
TS_FEB (reader S57_1)
    attributes: RCID integer, PRIM integer16, GRUP integer16, OBJL integer, RVER integer16, AGEN integer, FIDN integer, FIDS integer, LNAM char(16), LNAM_REFS{} char(16), FFPT_RIND{} integer16, CAT_TS integer, CURVEL double, DATEND char(254), DATSTA char(254), NOBJNM char(254), OBJNAM char(254), ORIENT double, PEREND char(254), PERSTA char(254), INFORM char(254), NINFOM char(254), NTXTDS char(254), SCAMAX integer, SCAMIN integer, TXTDSC char(254), RECDAT char(254), RECIND char(254), SORDAT char(254), SORIND char(254)
    -> AttributeManager_24
AttributeManager_24
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper_15
NullAttributeMapper_15
    ATTRCHOICE = Selected Attributes
    ATTRLIST = CURVEL
    NULL_TREATMENT = Missing
    SOURCE_ATTR_VAL = Empty
    -> 3_coastal_ts_feb_point (writer POSTGIS_1)
3_coastal_ts_feb_point (writer POSTGIS_1)
    attributes: fidn varchar(20), cat_ts varchar(80), curvel numeric(24,15), datend varchar(80), datsta varchar(80), nobjnm varchar(80), objnam varchar(80), orient numeric(24,15), perend varchar(80), persta varchar(80), inform varchar(80), ninfom varchar(80), ntxtds varchar(80), scamin numeric(24,15), txtdsc varchar(80), sordat varchar(80), sorind varchar(80)
TS_PAD (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), TS_TSP char(254), INFORM char(254), NINFOM char(254), NTXTDS char(254), SCAMAX integer, SCAMIN integer, TXTDSC char(254), RECDAT char(254), RECIND char(254), SORDAT char(254), SORIND char(254)
    -> AttributeManager_76
AttributeManager_76
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_ts_pad_point (writer POSTGIS_1)
3_coastal_ts_pad_point (writer POSTGIS_1)
    attributes: fidn varchar(20), nobjnm varchar(80), objnam varchar(80), ts_tsp varchar(254), inform varchar(80), ninfom varchar(80), ntxtds varchar(80), scamin numeric(24,15), txtdsc varchar(80), sordat varchar(80), sorind varchar(80)
UNSARE (reader S57_1)
    attributes: RCID integer, PRIM integer16, GRUP integer16, OBJL integer, RVER integer16, AGEN integer, FIDN integer, FIDS integer, LNAM char(16), LNAM_REFS{} char(16), FFPT_RIND{} integer16, INFORM char(254), NINFOM char(254), NTXTDS char(254), SCAMAX integer, SCAMIN integer, TXTDSC char(254), RECDAT char(254), RECIND char(254), SORDAT char(254), SORIND char(254)
    -> AttributeManager_77
AttributeManager_77
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE DSNM
    -> 3_coastal_unsare_polygon (writer POSTGIS_1)
3_coastal_unsare_polygon (writer POSTGIS_1)
    attributes: fidn varchar(20), inform varchar(254), ninfom varchar(80), ntxtds varchar(80), scamin numeric(24,15), txtdsc varchar(80), recdat varchar(80), recind varchar(80), sordat varchar(80), sorind varchar(80)
UWTROC (reader S57_1)
    attributes: RCID integer, PRIM integer16, GRUP integer16, OBJL integer, RVER integer16, AGEN integer, FIDN integer, FIDS integer, LNAM char(16), LNAM_REFS{} char(16), FFPT_RIND{} integer16, EXPSOU integer, NATSUR char(254), NATQUA char(254), NOBJNM char(254), OBJNAM char(254), QUASOU char(254), SOUACC double, STATUS char(254), TECSOU char(254), VALSOU double, VERDAT integer, WATLEV integer, INFORM char(254), NINFOM char(254), NTXTDS char(254), SCAMAX integer, SCAMIN integer, TXTDSC char(254), RECDAT char(254),
      RECIND char(254), SORDAT char(254), SORIND char(254)
    -> AttributeManager_78
AttributeManager_78
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper_6
NullAttributeMapper_6
    ATTRCHOICE = Selected Attributes
    ATTRLIST = VALSOU
    NULL_TREATMENT = Missing
    SOURCE_ATTR_VAL = Empty
    -> 3_coastal_uwtroc_point (writer POSTGIS_1)
3_coastal_uwtroc_point (writer POSTGIS_1)
    attributes: fidn varchar(20), expsou varchar(80), natsur varchar(80), natqua varchar(80), nobjnm varchar(80), objnam varchar(80), quasou varchar(80), souacc numeric(24,15), status varchar(80), tecsou varchar(80), valsou numeric(24,15), verdat varchar(80), watlev varchar(80), inform varchar(80), ninfom varchar(80), ntxtds varchar(80), scamin numeric(24,15), txtdsc varchar(80), sordat varchar(80), sorind varchar(80)
VEGATN (reader S57_1)
    attributes: RCID integer, PRIM integer16, GRUP integer16, OBJL integer, RVER integer16, AGEN integer, FIDN integer, FIDS integer, LNAM char(16), LNAM_REFS{} char(16), FFPT_RIND{} integer16, CATVEG char(254), CONVIS integer, ELEVAT double, HEIGHT double, NOBJNM char(254), OBJNAM char(254), VERACC double, VERDAT integer, VERLEN double, INFORM char(254), NINFOM char(254), NTXTDS char(254), SCAMAX integer, SCAMIN integer, TXTDSC char(254), RECDAT char(254), RECIND char(254), SORDAT char(254), SORIND char(254)
    -> AttributeManager_25
AttributeManager_25
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_7
GeometryFilter_7
    BREAK_AGG = No
    GEOM_PORT_NAMES = Point Area
    POINT -> 3_coastal_vegatn_point (writer POSTGIS_1)
    AREA -> 3_coastal_vegatn_polygon (writer POSTGIS_1)
3_coastal_vegatn_point (writer POSTGIS_1)
    attributes: fidn varchar(20), catveg varchar(80), convis varchar(80), elevat numeric(24,15), height numeric(24,15), nobjnm varchar(80), objnam varchar(80), veracc numeric(24,15), verdat varchar(80), verlen numeric(24,15), inform varchar(80), ninfom varchar(80), ntxtds varchar(80), scamin numeric(24,15), txtdsc varchar(80), sordat varchar(80), sorind varchar(80)
3_coastal_vegatn_polygon (writer POSTGIS_1)
    attributes: fidn varchar(20), catveg varchar(80), convis varchar(80), elevat numeric(24,15), height numeric(24,15), nobjnm varchar(80), objnam varchar(80), veracc numeric(24,15), verdat varchar(80), verlen numeric(24,15), inform varchar(80), ninfom varchar(80), ntxtds varchar(80), scamin numeric(24,15), txtdsc varchar(80), sordat varchar(80), sorind varchar(80)
WATTUR (reader S57_1)
    attributes: RCID integer, PRIM integer16, GRUP integer16, OBJL integer, RVER integer16, AGEN integer, FIDN integer, FIDS integer, LNAM char(16), LNAM_REFS{} char(16), FFPT_RIND{} integer16, CATWAT integer, NOBJNM char(254), OBJNAM char(254), INFORM char(254), NINFOM char(254), NTXTDS char(254), SCAMAX integer, SCAMIN integer, TXTDSC char(254), RECDAT char(254), RECIND char(254), SORDAT char(254), SORIND char(254)
    -> AttributeManager_79
AttributeManager_79
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_22
GeometryFilter_22
    BREAK_AGG = No
    GEOM_PORT_NAMES = Point Line Area
    POINT -> 3_coastal_wattur_point (writer POSTGIS_1)
    LINE -> 3_coastal_wattur_arc (writer POSTGIS_1)
    AREA -> 3_coastal_wattur_polygon (writer POSTGIS_1)
3_coastal_wattur_point (writer POSTGIS_1)
    attributes: fidn varchar(20), catwat varchar(80), nobjnm varchar(80), objnam varchar(80), inform varchar(254), ninfom varchar(80), ntxtds varchar(80), scamin numeric(24,15), txtdsc varchar(80), sordat varchar(80), sorind varchar(80)
3_coastal_wattur_arc (writer POSTGIS_1)
    attributes: fidn varchar(20), catwat varchar(80), nobjnm varchar(80), objnam varchar(80), inform varchar(254), ninfom varchar(80), ntxtds varchar(80), scamin numeric(24,15), txtdsc varchar(80), sordat varchar(80), sorind varchar(80)
3_coastal_wattur_polygon (writer POSTGIS_1)
    attributes: fidn varchar(20), catwat varchar(80), nobjnm varchar(80), objnam varchar(80), inform varchar(254), ninfom varchar(80), ntxtds varchar(80), scamin numeric(24,15), txtdsc varchar(80), sordat varchar(80), sorind varchar(80)
WEDKLP (reader S57_1)
    attributes: RCID integer, PRIM integer16, GRUP integer16, OBJL integer, RVER integer16, AGEN integer, FIDN integer, FIDS integer, LNAM char(16), LNAM_REFS{} char(16), FFPT_RIND{} integer16, CATWED integer, NOBJNM char(254), OBJNAM char(254), INFORM char(254), NINFOM char(254), NTXTDS char(254), SCAMAX integer, SCAMIN integer, TXTDSC char(254), RECDAT char(254), RECIND char(254), SORDAT char(254), SORIND char(254)
    -> AttributeManager_80
AttributeManager_80
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_23
GeometryFilter_23
    BREAK_AGG = No
    GEOM_PORT_NAMES = Point Area
    POINT -> 3_coastal_wedklp_point (writer POSTGIS_1)
    AREA -> 3_coastal_wedklp_polygon (writer POSTGIS_1)
3_coastal_wedklp_point (writer POSTGIS_1)
    attributes: fidn varchar(20), catwed varchar(80), nobjnm varchar(80), objnam varchar(80), inform varchar(80), ninfom varchar(80), ntxtds varchar(80), scamin numeric(24,15), txtdsc varchar(80), sordat varchar(80), sorind varchar(80)
3_coastal_wedklp_polygon (writer POSTGIS_1)
    attributes: fidn varchar(20), catwed varchar(80), nobjnm varchar(80), objnam varchar(80), inform varchar(80), ninfom varchar(80), ntxtds varchar(80), scamin numeric(24,15), txtdsc varchar(80), sordat varchar(80), sorind varchar(80)
WRECKS (reader S57_1)
    attributes: RCID integer, PRIM integer16, GRUP integer16, OBJL integer, RVER integer16, AGEN integer, FIDN integer, FIDS integer, LNAM char(16), LNAM_REFS{} char(16), FFPT_RIND{} integer16, CATWRK integer, CONRAD integer, CONVIS integer, EXPSOU integer, HEIGHT double, NOBJNM char(254), OBJNAM char(254), QUASOU char(254), SOUACC double, STATUS char(254), TECSOU char(254), VALSOU double, VERACC double, VERDAT integer, VERLEN double, WATLEV integer, INFORM char(254), NINFOM char(254), NTXTDS char(254),
      PICREP char(254), SCAMAX integer, SCAMIN integer, TXTDSC char(254), RECDAT char(254), RECIND char(254), SORDAT char(254), SORIND char(254)
    -> AttributeManager_42
AttributeManager_42
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper_10
NullAttributeMapper_10
    ATTRCHOICE = Selected Attributes
    ATTRLIST = VALSOU
    NULL_TREATMENT = Missing
    SOURCE_ATTR_VAL = Empty
    -> 3_coastal_wrecks_point (writer POSTGIS_1)
3_coastal_wrecks_point (writer POSTGIS_1)
    attributes: fidn varchar(20), catwrk varchar(80), conrad varchar(80), convis varchar(80), expsou varchar(80), height numeric(24,15), nobjnm varchar(80), objnam varchar(80), quasou varchar(80), souacc numeric(20,15), status varchar(80), tecsou varchar(80), valsou numeric(24,15), veracc numeric(24,15), verdat varchar(80), verlen numeric(24,15), watlev varchar(80), inform varchar(254), ninfom varchar(80), ntxtds varchar(80), picrep varchar(80), scamin numeric(24,15), txtdsc varchar(80), sordat varchar(80), sorind varchar(80)
ACHARE (reader S57_1)
    attributes: RCID integer, PRIM integer16, GRUP integer16, OBJL integer, RVER integer16, AGEN integer, FIDN integer, FIDS integer, LNAM char(16), LNAM_REFS{} char(16), FFPT_RIND{} integer16, CATACH char(254), DATEND char(254), DATSTA char(254), NOBJNM char(254), OBJNAM char(254), PEREND char(254), PERSTA char(254), RESTRN char(254), STATUS char(254), INFORM char(254), NINFOM char(254), NTXTDS char(254), SCAMAX integer, SCAMIN integer, TXTDSC char(254), RECDAT char(254), RECIND char(254), SORDAT char(254), SORIND char(254)
    -> AttributeManager_43
AttributeManager_43
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_10
GeometryFilter_10
    BREAK_AGG = No
    GEOM_PORT_NAMES = Point Area
    POINT -> 3_coastal_achare_point (writer POSTGIS_1)
    AREA -> 3_coastal_achare_polygon (writer POSTGIS_1)
3_coastal_achare_point (writer POSTGIS_1)
    attributes: fidn varchar(20), catach varchar(80), datend varchar(80), datsta varchar(80), nobjnm varchar(80), objnam varchar(80), perend varchar(80), persta varchar(80), restrn varchar(80), status varchar(80), inform varchar(150), ninfom varchar(80), ntxtds varchar(80), scamin numeric(24,15), txtdsc varchar(80), sordat varchar(80), sorind varchar(80)
3_coastal_achare_polygon (writer POSTGIS_1)
    attributes: fidn varchar(20), catach varchar(80), datend varchar(80), datsta varchar(80), nobjnm varchar(80), objnam varchar(80), perend varchar(80), persta varchar(80), restrn varchar(80), status varchar(80), inform varchar(150), ninfom varchar(80), ntxtds varchar(80), scamin numeric(24,15), txtdsc varchar(80), sordat varchar(80), sorind varchar(80)
ACHBRT (reader S57_1)
    attributes: RCID integer, PRIM integer16, GRUP integer16, OBJL integer, RVER integer16, AGEN integer, FIDN integer, FIDS integer, LNAM char(16), LNAM_REFS{} char(16), FFPT_RIND{} integer16, CATACH char(254), DATEND char(254), DATSTA char(254), NOBJNM char(254), OBJNAM char(254), PEREND char(254), PERSTA char(254), RADIUS double, STATUS char(254), INFORM char(254), NINFOM char(254), NTXTDS char(254), SCAMAX integer, SCAMIN integer, TXTDSC char(254), RECDAT char(254), RECIND char(254), SORDAT char(254), SORIND char(254)
    -> AttributeManager_44
AttributeManager_44
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_achbrt_point (writer POSTGIS_1)
3_coastal_achbrt_point (writer POSTGIS_1)
    attributes: fidn varchar(20), catach varchar(80), datend varchar(80), datsta varchar(80), nobjnm varchar(80), objnam varchar(80), perend varchar(80), persta varchar(80), radius numeric(24,15), status varchar(80), inform varchar(150), ninfom varchar(80), ntxtds varchar(80), scamin numeric(24,15), txtdsc varchar(80), sordat varchar(80), sorind varchar(80)
ADMARE (reader S57_1)
    attributes: RCID integer, PRIM integer16, GRUP integer16, OBJL integer, RVER integer16, AGEN integer, FIDN integer, FIDS integer, LNAM char(16), LNAM_REFS{} char(16), FFPT_RIND{} integer16, JRSDTN integer, NATION char(254), NOBJNM char(254), OBJNAM char(254), INFORM char(254), NINFOM char(254), NTXTDS char(254), PICREP char(254), SCAMAX integer, SCAMIN integer, TXTDSC char(254), RECDAT char(254), RECIND char(254), SORDAT char(254), SORIND char(254)
    -> AttributeManager_45
AttributeManager_45
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_admare_polygon (writer POSTGIS_1)
3_coastal_admare_polygon (writer POSTGIS_1)
    attributes: fidn varchar(20), jrsdtn varchar(80), nation varchar(80), nobjnm varchar(80), objnam varchar(80), inform varchar(150), ninfom varchar(80), ntxtds varchar(80), picrep varchar(80), scamin numeric(24,15), txtdsc varchar(80), sordat varchar(80), sorind varchar(80)
AIRARE (reader S57_1)
    attributes: RCID integer, PRIM integer16, GRUP integer16, OBJL integer, RVER integer16, AGEN integer, FIDN integer, FIDS integer, LNAM char(16), LNAM_REFS{} char(16), FFPT_RIND{} integer16, CATAIR char(254), CONDTN integer, CONVIS integer, NOBJNM char(254), OBJNAM char(254), STATUS char(254), INFORM char(254), NINFOM char(254), NTXTDS char(254), PICREP char(254), SCAMAX integer, SCAMIN integer, TXTDSC char(254), RECDAT char(254), RECIND char(254), SORDAT char(254), SORIND char(254)
    -> AttributeManager_46
AttributeManager_46
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_11
GeometryFilter_11
    BREAK_AGG = No
    GEOM_PORT_NAMES = Point Area
    POINT -> 3_coastal_airare_point (writer POSTGIS_1)
    AREA -> 3_coastal_airare_polygon (writer POSTGIS_1)
3_coastal_airare_point (writer POSTGIS_1)
    attributes: fidn varchar(20), catair varchar(80), condtn varchar(80), convis varchar(80), nobjnm varchar(80), objnam varchar(80), status varchar(80), inform varchar(80), ninfom varchar(80), ntxtds varchar(80), picrep varchar(80), scamin numeric(24,15), txtdsc varchar(80), sordat varchar(80), sorind varchar(80)
3_coastal_airare_polygon (writer POSTGIS_1)
    attributes: fidn varchar(20), catair varchar(80), condtn varchar(80), convis varchar(80), nobjnm varchar(80), objnam varchar(80), status varchar(80), inform varchar(254), ninfom varchar(80), ntxtds varchar(80), picrep varchar(80), scamin numeric(24,15), txtdsc varchar(80), sordat varchar(80), sorind varchar(80)
BCNCAR (reader S57_1)
    attributes: RCID integer, PRIM integer16, GRUP integer16, OBJL integer, RVER integer16, AGEN integer, FIDN integer, FIDS integer, LNAM char(16), LNAM_REFS{} char(16), FFPT_RIND{} integer16, BCNSHP integer, CATCAM integer, COLOUR char(254), COLPAT char(254), CONDTN integer, CONVIS integer, CONRAD integer, DATEND char(254), DATSTA char(254), ELEVAT double, HEIGHT double, MARSYS integer, NATCON char(254), NOBJNM char(254), OBJNAM char(254), PEREND char(254), PERSTA char(254), STATUS char(254), VERACC double,
      VERDAT integer, VERLEN double, INFORM char(254), NINFOM char(254), NTXTDS char(254), PICREP char(254), SCAMAX integer, SCAMIN integer, TXTDSC char(254), RECDAT char(254), RECIND char(254), SORDAT char(254), SORIND char(254)
    -> AttributeManager_47
AttributeManager_47
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_bcncar_point (writer POSTGIS_1)
3_coastal_bcncar_point (writer POSTGIS_1)
    attributes: fidn varchar(20), bcnshp varchar(80), catcam varchar(80), colour varchar(80), colpat varchar(80), condtn varchar(80), convis varchar(80), conrad varchar(80), datend varchar(80), datsta varchar(80), elevat numeric(24,15), height numeric(24,15), marsys varchar(80), natcon varchar(80), nobjnm varchar(80), objnam varchar(80), perend varchar(80), persta varchar(80), status varchar(80), veracc numeric(24,15), verdat varchar(80), verlen numeric(24,15), inform varchar(150), ninfom varchar(80), ntxtds varchar(80), picrep varchar(80), scamin numeric(24,15), txtdsc varchar(80), sordat varchar(80), sorind varchar(80)
BCNISD (reader S57_1)
    attributes: RCID integer, PRIM integer16, GRUP integer16, OBJL integer, RVER integer16, AGEN integer, FIDN integer, FIDS integer, LNAM char(16), LNAM_REFS{} char(16), FFPT_RIND{} integer16, BCNSHP integer, COLOUR char(254), COLPAT char(254), CONDTN integer, CONRAD integer, CONVIS integer, DATEND char(254), DATSTA char(254), ELEVAT double, HEIGHT double, MARSYS integer, NATCON char(254), NOBJNM char(254), OBJNAM char(254), PEREND char(254), PERSTA char(254), STATUS char(254), VERACC double, VERDAT integer,
      VERLEN double, INFORM char(254), NINFOM char(254), NTXTDS char(254), PICREP char(254), SCAMAX integer, SCAMIN integer, TXTDSC char(254), RECDAT char(254), RECIND char(254), SORDAT char(254), SORIND char(254)
    -> AttributeManager_48
AttributeManager_48
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_bcnisd_point (writer POSTGIS_1)
3_coastal_bcnisd_point (writer POSTGIS_1)
    attributes: fidn varchar(20), bcnshp varchar(80), colour varchar(80), colpat varchar(80), condtn varchar(80), conrad varchar(80), convis varchar(80), datend varchar(80), datsta varchar(80), elevat numeric(24,15), height numeric(24,15), marsys varchar(80), natcon varchar(80), nobjnm varchar(80), objnam varchar(80), perend varchar(80), persta varchar(80), status varchar(80), veracc numeric(24,15), verdat varchar(80), verlen numeric(24,15), inform varchar(150), ninfom varchar(80), ntxtds varchar(80), picrep varchar(80), scamin numeric(24,15), txtdsc varchar(80), sordat varchar(80), sorind varchar(80)
BCNLAT (reader S57_1)
    attributes: RCID integer, PRIM integer16, GRUP integer16, OBJL integer, RVER integer16, AGEN integer, FIDN integer, FIDS integer, LNAM char(16), LNAM_REFS{} char(16), FFPT_RIND{} integer16, BCNSHP integer, CATLAM integer, COLOUR char(254), COLPAT char(254), CONDTN integer, CONRAD integer, CONVIS integer, DATEND char(254), DATSTA char(254), ELEVAT double, HEIGHT double, MARSYS integer, NATCON char(254), NOBJNM char(254), OBJNAM char(254), PEREND char(254), PERSTA char(254), STATUS char(254), VERACC double,
      VERDAT integer, VERLEN double, INFORM char(254), NINFOM char(254), NTXTDS char(254), PICREP char(254), SCAMAX integer, SCAMIN integer, TXTDSC char(254), RECDAT char(254), RECIND char(254), SORDAT char(254), SORIND char(254)
    -> AttributeManager_49
AttributeManager_49
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_bcnlat_point (writer POSTGIS_1)
3_coastal_bcnlat_point (writer POSTGIS_1)
    attributes: fidn varchar(20), bcnshp varchar(80), catlam varchar(80), colour varchar(80), colpat varchar(80), condtn varchar(80), conrad varchar(80), convis varchar(80), datend varchar(80), datsta varchar(80), elevat numeric(24,10), height numeric(24,10), marsys varchar(80), natcon varchar(80), nobjnm varchar(80), objnam varchar(80), perend varchar(80), persta varchar(80), status varchar(80), veracc numeric(24,10), verdat varchar(80), verlen numeric(24,10), inform varchar(150), ninfom varchar(80), ntxtds varchar(80), picrep varchar(80), scamin numeric(24,10), txtdsc varchar(80), sordat varchar(80), sorind varchar(80)
BCNSAW (reader S57_1)
    attributes: RCID integer, PRIM integer16, GRUP integer16, OBJL integer, RVER integer16, AGEN integer, FIDN integer, FIDS integer, LNAM char(16), LNAM_REFS{} char(16), FFPT_RIND{} integer16, BCNSHP integer, COLOUR char(254), COLPAT char(254), CONDTN integer, CONRAD integer, CONVIS integer, DATEND char(254), DATSTA char(254), ELEVAT double, HEIGHT double, MARSYS integer, NATCON char(254), NOBJNM char(254), OBJNAM char(254), PEREND char(254), PERSTA char(254), STATUS char(254), VERACC double, VERDAT integer,
      VERLEN double, INFORM char(254), NINFOM char(254), NTXTDS char(254), PICREP char(254), SCAMAX integer, SCAMIN integer, TXTDSC char(254), RECDAT char(254), RECIND char(254), SORDAT char(254), SORIND char(254)
    -> AttributeManager_50
AttributeManager_50
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_bcnsaw_point (writer POSTGIS_1)
3_coastal_bcnsaw_point (writer POSTGIS_1)
    attributes: fidn varchar(20), bcnshp varchar(80), colour varchar(80), colpat varchar(80), condtn varchar(80), conrad varchar(80), convis varchar(80), datend varchar(80), datsta varchar(80), elevat numeric(24,15), height numeric(24,15), marsys varchar(80), natcon varchar(80), nobjnm varchar(80), objnam varchar(80), perend varchar(80), persta varchar(80), status varchar(80), veracc numeric(24,15), verdat varchar(80), verlen numeric(24,15), inform varchar(150), ninfom varchar(80), ntxtds varchar(80), picrep varchar(80), scamin numeric(24,15), txtdsc varchar(80), sordat varchar(80), sorind varchar(80)
BCNSPP (reader S57_1)
    attributes: RCID integer, PRIM integer16, GRUP integer16, OBJL integer, RVER integer16, AGEN integer, FIDN integer, FIDS integer, LNAM char(16), LNAM_REFS{} char(16), FFPT_RIND{} integer16, BCNSHP integer, CATSPM char(254), COLOUR char(254), COLPAT char(254), CONDTN integer, CONRAD integer, CONVIS integer, DATEND char(254), DATSTA char(254), ELEVAT double, HEIGHT double, MARSYS integer, NATCON char(254), NOBJNM char(254), OBJNAM char(254), PEREND char(254), PERSTA char(254), STATUS char(254), VERACC double,
      VERDAT integer, VERLEN double, INFORM char(254), NINFOM char(254), NTXTDS char(254), PICREP char(254), SCAMAX integer, SCAMIN integer, TXTDSC char(254), RECDAT char(254), RECIND char(254), SORDAT char(254), SORIND char(254)
    -> AttributeManager_26
AttributeManager_26
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_bcnspp_point (writer POSTGIS_1)
3_coastal_bcnspp_point (writer POSTGIS_1)
    attributes: fidn varchar(20), bcnshp varchar(80), catspm varchar(80), colour varchar(80), colpat varchar(80), condtn varchar(80), conrad varchar(80), convis varchar(80), datend varchar(80), datsta varchar(80), elevat numeric(24,15), height numeric(24,15), marsys varchar(80), natcon varchar(80), nobjnm varchar(80), objnam varchar(80), perend varchar(80), persta varchar(80), status varchar(80), veracc numeric(24,15), verdat varchar(80), verlen numeric(24,12), inform varchar(150), ninfom varchar(80), ntxtds varchar(80), picrep varchar(80), scamin numeric(24,15), txtdsc varchar(80), sordat varchar(80), sorind varchar(80)
BOYSPP (reader S57_1)
    attributes: RCID integer, PRIM integer16, GRUP integer16, OBJL integer, RVER integer16, AGEN integer, FIDN integer, FIDS integer, LNAM char(16), LNAM_REFS{} char(16), FFPT_RIND{} integer16, BOYSHP integer, CATSPM char(254), COLOUR char(254), COLPAT char(254), CONRAD integer, DATEND char(254), DATSTA char(254), MARSYS integer, NATCON char(254), NOBJNM char(254), OBJNAM char(254), PEREND char(254), PERSTA char(254), STATUS char(254), VERACC double, VERLEN double, INFORM char(254), NINFOM char(254), NTXTDS char(254),
      PICREP char(254), SCAMAX integer, SCAMIN integer, TXTDSC char(254), RECDAT char(254), RECIND char(254), SORDAT char(254), SORIND char(254)
    -> AttributeManager_28
AttributeManager_28
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_boyspp_point (writer POSTGIS_1)
3_coastal_boyspp_point (writer POSTGIS_1)
    attributes: fidn varchar(20), boyshp varchar(80), catspm varchar(80), colour varchar(80), colpat varchar(80), conrad varchar(80), datend varchar(80), datsta varchar(80), marsys varchar(80), natcon varchar(80), nobjnm varchar(80), objnam varchar(80), perend varchar(80), persta varchar(80), status varchar(80), veracc numeric(24,15), verlen numeric(24,15), inform varchar(150), ninfom varchar(80), ntxtds varchar(80), picrep varchar(80), scamin numeric(24,15), txtdsc varchar(80), sordat varchar(80), sorind varchar(80)
BOYCAR (reader S57_1)
    attributes: RCID integer, PRIM integer16, GRUP integer16, OBJL integer, RVER integer16, AGEN integer, FIDN integer, FIDS integer, LNAM char(16), LNAM_REFS{} char(16), FFPT_RIND{} integer16, BOYSHP integer, CATCAM integer, COLOUR char(254), COLPAT char(254), CONRAD integer, DATEND char(254), DATSTA char(254), MARSYS integer, NATCON char(254), NOBJNM char(254), OBJNAM char(254), PEREND char(254), PERSTA char(254), STATUS char(254), VERACC double, VERLEN double, INFORM char(254), NINFOM char(254), NTXTDS char(254),
      PICREP char(254), SCAMAX integer, SCAMIN integer, TXTDSC char(254), RECDAT char(254), RECIND char(254), SORDAT char(254), SORIND char(254)
    -> AttributeManager_27
AttributeManager_27
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_boycar_point (writer POSTGIS_1)
3_coastal_boycar_point (writer POSTGIS_1)
    attributes: fidn varchar(20), boyshp varchar(80), catcam varchar(80), colour varchar(80), colpat varchar(80), conrad varchar(80), datend varchar(80), datsta varchar(80), marsys varchar(80), natcon varchar(80), nobjnm varchar(80), objnam varchar(80), perend varchar(80), persta varchar(80), status varchar(80), veracc numeric(24,15), verlen numeric(24,15), inform varchar(150), ninfom varchar(80), ntxtds varchar(80), picrep varchar(80), scamin numeric(24,15), txtdsc varchar(80), sordat varchar(80), sorind varchar(80)
BOYISD (reader S57_1)
    attributes: RCID integer, PRIM integer16, GRUP integer16, OBJL integer, RVER integer16, AGEN integer, FIDN integer, FIDS integer, LNAM char(16), LNAM_REFS{} char(16), FFPT_RIND{} integer16, BOYSHP integer, COLOUR char(254), COLPAT char(254), CONRAD integer, DATEND char(254), DATSTA char(254), MARSYS integer, NATCON char(254), NOBJNM char(254), OBJNAM char(254), PEREND char(254), PERSTA char(254), STATUS char(254), VERACC double, VERLEN double, INFORM char(254), NINFOM char(254), NTXTDS char(254), PICREP char(254),
      SCAMAX integer, SCAMIN integer, TXTDSC char(254), RECDAT char(254), RECIND char(254), SORDAT char(254), SORIND char(254)
    -> AttributeManager_51
AttributeManager_51
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_boyisd_point (writer POSTGIS_1)
3_coastal_boyisd_point (writer POSTGIS_1)
    attributes: fidn varchar(20), boyshp varchar(80), colour varchar(80), colpat varchar(80), conrad varchar(80), datend varchar(80), datsta varchar(80), marsys varchar(80), natcon varchar(80), nobjnm varchar(80), objnam varchar(80), perend varchar(80), persta varchar(80), status varchar(80), veracc numeric(24,15), verlen numeric(24,15), inform varchar(150), ninfom varchar(80), ntxtds varchar(80), picrep varchar(80), scamin numeric(24,15), txtdsc varchar(80), sordat varchar(80), sorind varchar(80)
BOYLAT (reader S57_1)
    attributes: RCID integer, PRIM integer16, GRUP integer16, OBJL integer, RVER integer16, AGEN integer, FIDN integer, FIDS integer, LNAM char(16), LNAM_REFS{} char(16), FFPT_RIND{} integer16, BOYSHP integer, CATLAM integer, COLOUR char(254), COLPAT char(254), CONRAD integer, DATEND char(254), DATSTA char(254), MARSYS integer, NATCON char(254), NOBJNM char(254), OBJNAM char(254), PEREND char(254), PERSTA char(254), STATUS char(254), VERACC double, VERLEN double, INFORM char(254), NINFOM char(254), NTXTDS char(254),
      PICREP char(254), SCAMAX integer, SCAMIN integer, TXTDSC char(254), RECDAT char(254), RECIND char(254), SORDAT char(254), SORIND char(254)
    -> AttributeManager_52
AttributeManager_52
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_boylat_point (writer POSTGIS_1)
3_coastal_boylat_point (writer POSTGIS_1)
    attributes: fidn varchar(20), boyshp varchar(80), catlam varchar(80), colour varchar(80), colpat varchar(80), conrad varchar(80), datend varchar(80), datsta varchar(80), marsys varchar(80), natcon varchar(80), nobjnm varchar(80), objnam varchar(80), perend varchar(80), persta varchar(80), status varchar(80), veracc numeric(24,15), verlen numeric(24,15), inform varchar(150), ninfom varchar(80), ntxtds varchar(80), picrep varchar(80), scamin numeric(24,15), txtdsc varchar(80), sordat varchar(80), sorind varchar(80)
BOYSAW (reader S57_1)
    attributes: RCID integer, PRIM integer16, GRUP integer16, OBJL integer, RVER integer16, AGEN integer, FIDN integer, FIDS integer, LNAM char(16), LNAM_REFS{} char(16), FFPT_RIND{} integer16, BOYSHP integer, COLOUR char(254), COLPAT char(254), CONRAD integer, DATEND char(254), DATSTA char(254), MARSYS integer, NATCON char(254), NOBJNM char(254), OBJNAM char(254), PEREND char(254), PERSTA char(254), STATUS char(254), VERACC double, VERLEN double, INFORM char(254), NINFOM char(254), NTXTDS char(254), PICREP char(254),
      SCAMAX integer, SCAMIN integer, TXTDSC char(254), RECDAT char(254), RECIND char(254), SORDAT char(254), SORIND char(254)
    -> AttributeManager_53
AttributeManager_53
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_boysaw_point (writer POSTGIS_1)
3_coastal_boysaw_point (writer POSTGIS_1)
    attributes: fidn varchar(20), boyshp varchar(80), colour varchar(80), colpat varchar(80), conrad varchar(80), datend varchar(80), datsta varchar(80), marsys varchar(80), natcon varchar(80), nobjnm varchar(80), objnam varchar(80), perend varchar(80), persta varchar(80), status varchar(80), veracc numeric(20,10), verlen numeric(20,10), inform varchar(150), ninfom varchar(80), ntxtds varchar(80), picrep varchar(80), scamin numeric(20,10), txtdsc varchar(80), sordat varchar(80), sorind varchar(80)
BRIDGE (reader S57_1)
    attributes: RCID integer, PRIM integer16, GRUP integer16, OBJL integer, RVER integer16, AGEN integer, FIDN integer, FIDS integer, LNAM char(16), LNAM_REFS{} char(16), FFPT_RIND{} integer16, CATBRG char(254), COLOUR char(254), COLPAT char(254), CONDTN integer, CONRAD integer, CONVIS integer, DATEND char(254), DATSTA char(254), HORACC double, HORCLR double, NATCON char(254), NOBJNM char(254), OBJNAM char(254), VERACC double, VERCCL double, VERCLR double, VERCOP double, VERDAT integer, INFORM char(254),
      NINFOM char(254), NTXTDS char(254), PICREP char(254), SCAMAX integer, SCAMIN integer, TXTDSC char(254), RECDAT char(254), RECIND char(254), SORDAT char(254), SORIND char(254)
    -> AttributeManager_54
AttributeManager_54
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_12
GeometryFilter_12
    BREAK_AGG = No
    GEOM_PORT_NAMES = Area Line
    AREA -> NullAttributeMapper_3
    LINE -> NullAttributeMapper_18
NullAttributeMapper_3
    ATTRCHOICE = Selected Attributes
    ATTRLIST = VERCLR
    NULL_TREATMENT = Missing
    SOURCE_ATTR_VAL = Empty
    -> 3_coastal_bridge_polygon (writer POSTGIS_1)
3_coastal_bridge_polygon (writer POSTGIS_1)
    attributes: fidn varchar(20), catbrg varchar(80), colour varchar(80), colpat varchar(80), condtn varchar(80), conrad varchar(80), convis varchar(80), datend varchar(80), datsta varchar(80), horacc numeric(24,15), horclr numeric(24,15), natcon varchar(80), nobjnm varchar(80), objnam varchar(80), veracc numeric(24,15), verccl numeric(24,15), verclr numeric(24,15), vercop numeric(24,15), verdat varchar(80), inform varchar(150), ninfom varchar(80), ntxtds varchar(80), picrep varchar(80), scamin numeric(24,15), txtdsc varchar(80), sordat varchar(80), sorind varchar(80)
NullAttributeMapper_18
    ATTRCHOICE = Selected Attributes
    ATTRLIST = VERCLR
    NULL_TREATMENT = Missing
    SOURCE_ATTR_VAL = Empty
    -> 3_coastal_bridge_arc (writer POSTGIS_1)
3_coastal_bridge_arc (writer POSTGIS_1)
    attributes: fidn varchar(20), catbrg varchar(80), colour varchar(80), colpat varchar(80), condtn varchar(80), conrad varchar(80), convis varchar(80), datend varchar(80), datsta varchar(80), horacc numeric(24,15), horclr numeric(24,15), natcon varchar(80), nobjnm varchar(80), objnam varchar(80), veracc numeric(24,15), verccl numeric(24,15), verclr numeric(24,15), vercop numeric(24,15), verdat varchar(80), inform varchar(254), ninfom varchar(80), ntxtds varchar(80), picrep varchar(80), scamin numeric(24,15), txtdsc varchar(80), sordat varchar(80), sorind varchar(80)
BUAARE (reader S57_1)
    attributes: RCID integer, PRIM integer16, GRUP integer16, OBJL integer, RVER integer16, AGEN integer, FIDN integer, FIDS integer, LNAM char(16), LNAM_REFS{} char(16), FFPT_RIND{} integer16, CATBUA integer, CONDTN integer, CONRAD integer, CONVIS integer, HEIGHT double, NOBJNM char(254), OBJNAM char(254), VERACC double, VERDAT integer, INFORM char(254), NINFOM char(254), NTXTDS char(254), PICREP char(254), SCAMAX integer, SCAMIN integer, TXTDSC char(254), RECDAT char(254), RECIND char(254), SORDAT char(254),
      SORIND char(254)
    -> AttributeManager
AttributeManager
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE PICREP
      REMOVE SCAMAX
      REMOVE RECDAT
      REMOVE RECIND
      REMOVE DSNM
    -> GeometryFilter_2
GeometryFilter_2
    BREAK_AGG = No
    GEOM_PORT_NAMES = Point Area
    POINT -> 3_coastal_buaare_point (writer POSTGIS_1)
    AREA -> 3_coastal_buaare_polygon (writer POSTGIS_1)
3_coastal_buaare_point (writer POSTGIS_1)
    attributes: fidn varchar(20), catbua varchar(80), condtn varchar(80), conrad varchar(80), convis varchar(80), height numeric(24,15), nobjnm varchar(80), objnam varchar(80), veracc numeric(24,15), verdat varchar(80), inform varchar(150), ninfom varchar(80), ntxtds varchar(80), scamin numeric(24,15), txtdsc varchar(80), sordat varchar(80), sorind varchar(80)
3_coastal_buaare_polygon (writer POSTGIS_1)
    attributes: fidn varchar(20), catbua varchar(80), condtn varchar(80), conrad varchar(80), convis varchar(80), height numeric(24,15), nobjnm varchar(80), objnam varchar(80), veracc numeric(24,15), verdat varchar(80), inform varchar(150), ninfom varchar(80), ntxtds varchar(80), scamin numeric(24,15), txtdsc varchar(80), sordat varchar(80), sorind varchar(80)
BUISGL (reader S57_1)
    attributes: RCID integer, PRIM integer16, GRUP integer16, OBJL integer, RVER integer16, AGEN integer, FIDN integer, FIDS integer, LNAM char(16), LNAM_REFS{} char(16), FFPT_RIND{} integer16, BUISHP integer, COLOUR char(254), COLPAT char(254), CONDTN integer, CONRAD integer, CONVIS integer, ELEVAT double, FUNCTN char(254), HEIGHT double, NATCON char(254), NOBJNM char(254), OBJNAM char(254), STATUS char(254), VERACC double, VERDAT integer, VERLEN double, INFORM char(254), NINFOM char(254), NTXTDS char(254),
      PICREP char(254), SCAMAX integer, SCAMIN integer, TXTDSC char(254), RECDAT char(254), RECIND char(254), SORDAT char(254), SORIND char(254)
    -> AttributeManager_55
AttributeManager_55
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_13
GeometryFilter_13
    BREAK_AGG = No
    GEOM_PORT_NAMES = Point Area
    POINT -> 3_coastal_buisgl_point (writer POSTGIS_1)
    AREA -> 3_coastal_buisgl_polygon (writer POSTGIS_1)
3_coastal_buisgl_point (writer POSTGIS_1)
    attributes: fidn varchar(20), buishp varchar(80), colour varchar(80), colpat varchar(80), condtn varchar(80), conrad varchar(80), convis varchar(80), elevat numeric(24,15), functn varchar(80), height numeric(24,15), natcon varchar(80), nobjnm varchar(80), objnam varchar(80), status varchar(80), veracc numeric(24,15), verdat varchar(80), verlen numeric(24,15), inform varchar(150), ninfom varchar(80), ntxtds varchar(80), picrep varchar(80), scamin numeric(24,15), txtdsc varchar(80), sordat varchar(80), sorind varchar(80)
3_coastal_buisgl_polygon (writer POSTGIS_1)
    attributes: fidn varchar(20), buishp varchar(80), colour varchar(80), colpat varchar(80), condtn varchar(80), conrad varchar(80), convis varchar(80), elevat numeric(24,15), functn varchar(80), height numeric(24,15), natcon varchar(80), nobjnm varchar(80), objnam varchar(80), status varchar(80), veracc numeric(24,15), verdat varchar(80), verlen numeric(24,15), inform varchar(150), ninfom varchar(80), ntxtds varchar(80), picrep varchar(80), scamin numeric(24,15), txtdsc varchar(80), sordat varchar(80), sorind varchar(80)
C_AGGR (reader S57_1)
    attributes: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
CANALS (reader S57_1)
    attributes: RCID integer, PRIM integer16, GRUP integer16, OBJL integer, RVER integer16, AGEN integer, FIDN integer, FIDS integer, LNAM char(16), LNAM_REFS{} char(16), FFPT_RIND{} integer16, CATCAN integer, CONDTN integer, DATEND char(254), DATSTA char(254), HORACC double, HORCLR double, HORWID double, NOBJNM char(254), OBJNAM char(254), STATUS char(254), INFORM char(254), NINFOM char(254), NTXTDS char(254), SCAMAX integer, SCAMIN integer, TXTDSC char(254), RECDAT char(254), RECIND char(254), SORDAT char(254),
      SORIND char(254)
    -> AttributeManager_56
AttributeManager_56
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_canals_polygon (writer POSTGIS_1)
3_coastal_canals_polygon (writer POSTGIS_1)
    attributes: fidn varchar(20), catcan varchar(80), condtn varchar(80), datend varchar(80), datsta varchar(80), horacc numeric(24,15), horclr numeric(24,15), horwid numeric(24,15), nobjnm varchar(80), objnam varchar(80), status varchar(80), inform varchar(150), ninfom varchar(80), ntxtds varchar(80), scamin numeric(24,15), txtdsc varchar(80), sordat varchar(80), sorind varchar(80)
CBLARE (reader S57_1)
    attributes: RCID integer, PRIM integer16, GRUP integer16, OBJL integer, RVER integer16, AGEN integer, FIDN integer, FIDS integer, LNAM char(16), LNAM_REFS{} char(16), FFPT_RIND{} integer16, CATCBL integer, DATEND char(254), DATSTA char(254), NOBJNM char(254), OBJNAM char(254), RESTRN char(254), STATUS char(254), INFORM char(254), NINFOM char(254), NTXTDS char(254), SCAMAX integer, SCAMIN integer, TXTDSC char(254), RECDAT char(254), RECIND char(254), SORDAT char(254), SORIND char(254)
    -> AttributeManager_57
AttributeManager_57
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_cblare_polygon (writer POSTGIS_1)
3_coastal_cblare_polygon (writer POSTGIS_1)
    attributes: fidn varchar(20), catcbl varchar(80), datend varchar(80), datsta varchar(80), nobjnm varchar(80), objnam varchar(80), restrn varchar(80), status varchar(80), inform varchar(150), ninfom varchar(80), ntxtds varchar(80), scamin numeric(24,15), txtdsc varchar(80), sordat varchar(80), sorind varchar(80)
CBLOHD (reader S57_1)
    attributes: RCID integer, PRIM integer16, GRUP integer16, OBJL integer, RVER integer16, AGEN integer, FIDN integer, FIDS integer, LNAM char(16), LNAM_REFS{} char(16), FFPT_RIND{} integer16, CATCBL integer, CONDTN integer, CONRAD integer, CONVIS integer, DATEND char(254), DATSTA char(254), ICEFAC double, NOBJNM char(254), OBJNAM char(254), STATUS char(254), VERACC double, VERCLR double, VERCSA double, VERDAT integer, INFORM char(254), NINFOM char(254), NTXTDS char(254), SCAMAX integer, SCAMIN integer,
      TXTDSC char(254), RECDAT char(254), RECIND char(254), SORDAT char(254), SORIND char(254)
    -> AttributeManager_58
AttributeManager_58
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper_16
NullAttributeMapper_16
    ATTRCHOICE = Selected Attributes
    ATTRLIST = VERCLR VERCSA
    NULL_TREATMENT = Missing
    SOURCE_ATTR_VAL = Empty
    -> 3_coastal_cblohd_arc (writer POSTGIS_1)
3_coastal_cblohd_arc (writer POSTGIS_1)
    attributes: fidn varchar(20), catcbl varchar(80), condtn varchar(80), conrad varchar(80), convis varchar(80), datend varchar(80), datsta varchar(80), icefac numeric(24,15), nobjnm varchar(80), objnam varchar(80), status varchar(80), veracc numeric(24,15), verclr numeric(24,15), vercsa numeric(24,15), verdat varchar(80), inform varchar(150), ninfom varchar(80), ntxtds varchar(80), scamin numeric(24,15), txtdsc varchar(80), sordat varchar(80), sorind varchar(80)
CBLSUB (reader S57_1)
    attributes: RCID integer, PRIM integer16, GRUP integer16, OBJL integer, RVER integer16, AGEN integer, FIDN integer, FIDS integer, LNAM char(16), LNAM_REFS{} char(16), FFPT_RIND{} integer16, BURDEP double, CATCBL integer, CONDTN integer, DATEND char(254), DATSTA char(254), NOBJNM char(254), OBJNAM char(254), STATUS char(254), VERDAT integer, INFORM char(254), NINFOM char(254), NTXTDS char(254), SCAMAX integer, SCAMIN integer, TXTDSC char(254), RECDAT char(254), RECIND char(254), SORDAT char(254), SORIND char(254)
    -> AttributeManager_2
AttributeManager_2
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      SET_TO drval1
      SET_TO drval2
      REMOVE SCAMAX
      REMOVE RECDAT
      REMOVE RECIND
      REMOVE DSNM
    -> NullAttributeMapper_8
NullAttributeMapper_8
    ATTRCHOICE = Selected Attributes
    ATTRLIST = drval1 drval2
    NULL_TREATMENT = Missing
    SOURCE_ATTR_VAL = Empty
    -> 3_coastal_cblsub_arc (writer POSTGIS_1)
3_coastal_cblsub_arc (writer POSTGIS_1)
    attributes: fidn varchar(20), burdep numeric(24,15), catcbl varchar(80), condtn varchar(80), datend varchar(80), datsta varchar(80), drval1 numeric(24,15), drval2 numeric(24,15), nobjnm varchar(80), objnam varchar(80), status varchar(80), verdat varchar(80), inform varchar(80), ninfom varchar(80), ntxtds varchar(80), scamin numeric(24,15), txtdsc varchar(80), sordat varchar(80), sorind varchar(80)
COALNE (reader S57_1)
    attributes: RCID integer, PRIM integer16, GRUP integer16, OBJL integer, RVER integer16, AGEN integer, FIDN integer, FIDS integer, LNAM char(16), LNAM_REFS{} char(16), FFPT_RIND{} integer16, CATCOA integer, COLOUR char(254), CONRAD integer, CONVIS integer, ELEVAT double, NOBJNM char(254), OBJNAM char(254), VERACC double, VERDAT integer, INFORM char(254), NINFOM char(254), NTXTDS char(254), PICREP char(254), SCAMAX integer, SCAMIN integer, TXTDSC char(254), RECDAT char(254), RECIND char(254), SORDAT char(254),
      SORIND char(254)
    -> AttributeManager_3
AttributeManager_3
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_coalne_arc (writer POSTGIS_1)
3_coastal_coalne_arc (writer POSTGIS_1)
    attributes: fidn varchar(20), catcoa varchar(80), colour varchar(80), conrad varchar(80), convis varchar(80), elevat numeric(24,15), nobjnm varchar(80), objnam varchar(80), veracc numeric(24,15), verdat varchar(80), inform varchar(150), ninfom varchar(80), ntxtds varchar(80), picrep varchar(80), scamin numeric(24,15), txtdsc varchar(80), sordat varchar(80), sorind varchar(80)
CTNARE (reader S57_1)
    attributes: RCID integer, PRIM integer16, GRUP integer16, OBJL integer, RVER integer16, AGEN integer, FIDN integer, FIDS integer, LNAM char(16), LNAM_REFS{} char(16), FFPT_RIND{} integer16, DATEND char(254), DATSTA char(254), PEREND char(254), PERSTA char(254), INFORM char(254), NINFOM char(254), NTXTDS char(254), SCAMAX integer, SCAMIN integer, TXTDSC char(254), RECDAT char(254), RECIND char(254), SORDAT char(254), SORIND char(254)
    -> AttributeManager_29
AttributeManager_29
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_8
GeometryFilter_8
    BREAK_AGG = No
    GEOM_PORT_NAMES = Point Area
    POINT -> 3_coastal_ctnare_point (writer POSTGIS_1)
    AREA -> 3_coastal_ctnare_polygon (writer POSTGIS_1)
3_coastal_ctnare_point (writer POSTGIS_1)
    attributes: fidn varchar(20), datend varchar(80), datsta varchar(80), perend varchar(80), persta varchar(80), inform varchar(2000), ninfom varchar(80), ntxtds varchar(80), scamin numeric(24,15), txtdsc varchar(80), sordat varchar(80), sorind varchar(80)
3_coastal_ctnare_polygon (writer POSTGIS_1)
    attributes: fidn varchar(20), datend varchar(80), datsta varchar(80), perend varchar(80), persta varchar(80), inform varchar(254), ninfom varchar(80), ntxtds varchar(80), scamin numeric(24,15), txtdsc varchar(80), sordat varchar(80), sorind varchar(80)
CURENT (reader S57_1)
    attributes: RCID integer, PRIM integer16, GRUP integer16, OBJL integer, RVER integer16, AGEN integer, FIDN integer, FIDS integer, LNAM char(16), LNAM_REFS{} char(16), FFPT_RIND{} integer16, CURVEL double, DATEND char(254), DATSTA char(254), NOBJNM char(254), OBJNAM char(254), ORIENT double, PEREND char(254), PERSTA char(254), INFORM char(254), NINFOM char(254), SCAMAX integer, SCAMIN integer, RECDAT char(254), RECIND char(254), SORDAT char(254), SORIND char(254)
    -> AttributeManager_4
AttributeManager_4
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper_7
NullAttributeMapper_7
    ATTRCHOICE = Selected Attributes
    ATTRLIST = CURVEL
    NULL_TREATMENT = Missing
    SOURCE_ATTR_VAL = Empty
    -> NullAttributeMapper_13
NullAttributeMapper_13
    ATTRCHOICE = Selected Attributes
    ATTRLIST = ORIENT
    NULL_TREATMENT = Missing
    SOURCE_ATTR_VAL = Empty
    -> 3_coastal_curent_point (writer POSTGIS_1)
3_coastal_curent_point (writer POSTGIS_1)
    attributes: fidn varchar(20), curvel numeric(24,15), datend varchar(80), datsta varchar(80), nobjnm varchar(80), objnam varchar(80), orient numeric(24,15), perend varchar(80), persta varchar(80), inform varchar(80), ninfom varchar(80), scamin numeric(24,15), sordat varchar(80), sorind varchar(80)
DAYMAR (reader S57_1)
    attributes: RCID integer, PRIM integer16, GRUP integer16, OBJL integer, RVER integer16, AGEN integer, FIDN integer, FIDS integer, LNAM char(16), LNAM_REFS{} char(16), FFPT_RIND{} integer16, CATSPM char(254), COLOUR char(254), COLPAT char(254), DATEND char(254), DATSTA char(254), ELEVAT double, HEIGHT double, NATCON char(254), NOBJNM char(254), OBJNAM char(254), PEREND char(254), PERSTA char(254), STATUS char(254), TOPSHP integer, VERACC double, VERDAT integer, VERLEN double, INFORM char(254), NINFOM char(254),
      NTXTDS char(254), SCAMAX integer, SCAMIN integer, TXTDSC char(254), RECDAT char(254), RECIND char(254), SORDAT char(254), SORIND char(254)
    -> AttributeManager_59
AttributeManager_59
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_daymar_point (writer POSTGIS_1)
3_coastal_daymar_point (writer POSTGIS_1)
    attributes: fidn varchar(20), catspm varchar(80), colour varchar(80), colpat varchar(80), datend varchar(80), datsta varchar(80), elevat numeric(24,15), height numeric(24,15), natcon varchar(80), nobjnm varchar(80), objnam varchar(80), perend varchar(80), persta varchar(80), status varchar(80), topshp varchar(80), veracc numeric(24,15), verdat varchar(80), verlen numeric(24,15), inform varchar(150), ninfom varchar(80), ntxtds varchar(80), scamin numeric(24,15), txtdsc varchar(80), sordat varchar(80), sorind varchar(80)
DEPARE (reader S57_1)
    attributes: RCID integer, PRIM integer16, GRUP integer16, OBJL integer, RVER integer16, AGEN integer, FIDN integer, FIDS integer, LNAM char(16), LNAM_REFS{} char(16), FFPT_RIND{} integer16, DRVAL1 double, DRVAL2 double, QUASOU char(254), SOUACC double, VERDAT integer, INFORM char(254), NINFOM char(254), NTXTDS char(254), SCAMAX integer, SCAMIN integer, TXTDSC char(254), RECDAT char(254), RECIND char(254), SORDAT char(254), SORIND char(254)
    -> AttributeManager_6
AttributeManager_6
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper
NullAttributeMapper
    ATTRCHOICE = Selected Attributes
    ATTRLIST = DRVAL1
    NULL_TREATMENT = Missing
    SOURCE_ATTR_VAL = Empty
    -> 3_coastal_depare_polygon (writer POSTGIS_1)
3_coastal_depare_polygon (writer POSTGIS_1)
    attributes: fidn varchar(20), drval1 numeric(24,15), drval2 numeric(24,15), quasou varchar(80), souacc numeric(24,15), verdat varchar(80), inform varchar(80), ninfom varchar(80), ntxtds varchar(80), scamin numeric(24,15), txtdsc varchar(80), sordat varchar(80), sorind varchar(80)
DEPCNT (reader S57_1)
    attributes: RCID integer, PRIM integer16, GRUP integer16, OBJL integer, RVER integer16, AGEN integer, FIDN integer, FIDS integer, LNAM char(16), LNAM_REFS{} char(16), FFPT_RIND{} integer16, VALDCO double, VERDAT integer, INFORM char(254), NINFOM char(254), NTXTDS char(254), SCAMAX integer, SCAMIN integer, TXTDSC char(254), RECDAT char(254), RECIND char(254), SORDAT char(254), SORIND char(254)
    -> AttributeManager_7
AttributeManager_7
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      SET_TO HYPCAT
      REMOVE DSNM
    -> NullAttributeMapper_9
NullAttributeMapper_9
    ATTRCHOICE = Selected Attributes
    ATTRLIST = HYPCAT
    NULL_TREATMENT = Missing
    SOURCE_ATTR_VAL = Empty
    -> 3_coastal_depcnt_arc (writer POSTGIS_1)
3_coastal_depcnt_arc (writer POSTGIS_1)
    attributes: fidn varchar(20), valdco numeric(24,15), verdat varchar(80), inform varchar(80), ninfom varchar(80), ntxtds varchar(80), scamin numeric(24,15), txtdsc varchar(80), sordat varchar(80), sorind varchar(80), hypcat numeric(24,15)
DMPGRD (reader S57_1)
    attributes: RCID integer, PRIM integer16, GRUP integer16, OBJL integer, RVER integer16, AGEN integer, FIDN integer, FIDS integer, LNAM char(16), LNAM_REFS{} char(16), FFPT_RIND{} integer16, CATDPG char(254), NOBJNM char(254), OBJNAM char(254), RESTRN char(254), STATUS char(254), INFORM char(254), NINFOM char(254), NTXTDS char(254), SCAMAX integer, SCAMIN integer, TXTDSC char(254), RECDAT char(254), RECIND char(254), SORDAT char(254), SORIND char(254)
    -> AttributeManager_8
AttributeManager_8
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_dmpgrd_polygon (writer POSTGIS_1)
3_coastal_dmpgrd_polygon (writer POSTGIS_1)
    attributes: fidn varchar(20), catdpg varchar(80), nobjnm varchar(80), objnam varchar(80), restrn varchar(80), status varchar(80), inform varchar(80), ninfom varchar(80), ntxtds varchar(80), scamin numeric(24,15), txtdsc varchar(80), sordat varchar(80), sorind varchar(80)
DRGARE (reader S57_1)
    attributes: RCID integer, PRIM integer16, GRUP integer16, OBJL integer, RVER integer16, AGEN integer, FIDN integer, FIDS integer, LNAM char(16), LNAM_REFS{} char(16), FFPT_RIND{} integer16, DRVAL1 double, DRVAL2 double, NOBJNM char(254), OBJNAM char(254), QUASOU char(254), RESTRN char(254), SOUACC double, TECSOU char(254), VERDAT integer, INFORM char(254), NINFOM char(254), NTXTDS char(254), SCAMAX integer, SCAMIN integer, TXTDSC char(254), RECDAT char(254), RECIND char(254), SORDAT char(254), SORIND char(254)
    -> AttributeManager_60
AttributeManager_60
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_drgare_polygon (writer POSTGIS_1)
3_coastal_drgare_polygon (writer POSTGIS_1)
    attributes: fidn varchar(20), drval1 numeric(24,15), drval2 numeric(24,15), nobjnm varchar(80), objnam varchar(80), quasou varchar(80), restrn varchar(80), souacc numeric(24,15), tecsou varchar(80), verdat varchar(20), inform varchar(80), ninfom varchar(80), ntxtds varchar(80), scamin numeric(24,10), txtdsc varchar(80), sordat varchar(80), sorind varchar(80)
FOGSIG (reader S57_1)
    attributes: RCID integer, PRIM integer16, GRUP integer16, OBJL integer, RVER integer16, AGEN integer, FIDN integer, FIDS integer, LNAM char(16), LNAM_REFS{} char(16), FFPT_RIND{} integer16, CATFOG integer, DATEND char(254), DATSTA char(254), NOBJNM char(254), OBJNAM char(254), SIGFRQ integer, SIGGEN integer, SIGGRP char(254), SIGPER double, SIGSEQ char(254), STATUS char(254), VALMXR double, INFORM char(254), NINFOM char(254), NTXTDS char(254), SCAMAX integer, SCAMIN integer, TXTDSC char(254), RECDAT char(254),
      RECIND char(254), SORDAT char(254), SORIND char(254)
    -> AttributeManager_5
AttributeManager_5
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_fogsig_point (writer POSTGIS_1)
3_coastal_fogsig_point (writer POSTGIS_1)
    attributes: fidn varchar(20), catfog varchar(80), datend varchar(80), datsta varchar(80), nobjnm varchar(80), objnam varchar(80), sigfrq numeric(24,15), siggen varchar(80), siggrp varchar(80), sigper numeric(24,15), sigseq varchar(80), status varchar(80), valmxr numeric(24,15), inform varchar(80), ninfom varchar(80), ntxtds varchar(80), scamin numeric(24,15), txtdsc varchar(80), sordat varchar(80), sorind varchar(80)
HRBARE (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), STATUS char(254), INFORM char(254), NINFOM char(254), NTXTDS char(254), SCAMAX integer, SCAMIN integer, TXTDSC char(254), RECDAT char(254), RECIND char(254), SORDAT char(254), SORIND char(254)
    -> AttributeManager_61
AttributeManager_61
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_hrbare_polygon (writer POSTGIS_1)
3_coastal_hrbare_polygon (writer POSTGIS_1)
    attributes: fidn varchar(20), nobjnm varchar(80), objnam varchar(80), status varchar(80), inform varchar(2000), ninfom varchar(80), ntxtds varchar(80), scamin numeric(24,15), txtdsc varchar(80), sordat varchar(80), sorind varchar(80)
HRBFAC (reader S57_1)
    attributes: RCID integer, PRIM integer16, GRUP integer16, OBJL integer, RVER integer16, AGEN integer, FIDN integer, FIDS integer, LNAM char(16), LNAM_REFS{} char(16), FFPT_RIND{} integer16, CATHAF char(254), CONDTN integer, DATEND char(254), DATSTA char(254), NATCON char(254), NOBJNM char(254), OBJNAM char(254), PEREND char(254), PERSTA char(254), STATUS char(254), INFORM char(254), NINFOM char(254), NTXTDS char(254), SCAMAX integer, SCAMIN integer, TXTDSC char(254), RECDAT char(254), RECIND char(254), SORDAT char(254),
      SORIND char(254)
    -> AttributeManager_62
AttributeManager_62
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_hrbfac_point (writer POSTGIS_1)
3_coastal_hrbfac_point (writer POSTGIS_1)
    attributes: fidn varchar(20), cathaf varchar(80), condtn varchar(80), datend varchar(80), datsta varchar(80), natcon varchar(80), nobjnm varchar(80), objnam varchar(80), perend varchar(80), persta varchar(80), status varchar(80), inform varchar(80), ninfom varchar(80), ntxtds varchar(80), scamin numeric(24,15), txtdsc varchar(80), sordat varchar(80), sorind varchar(80)
HULKES (reader S57_1)
    attributes: RCID integer, PRIM integer16, GRUP integer16, OBJL integer, RVER integer16, AGEN integer, FIDN integer, FIDS integer, LNAM char(16), LNAM_REFS{} char(16), FFPT_RIND{} integer16, CATHLK char(254), COLOUR char(254), COLPAT char(254), CONRAD integer, CONVIS integer, HORACC double, HORLEN double, HORWID double, NOBJNM char(254), OBJNAM char(254), VERACC double, VERLEN double, CONDTN integer, INFORM char(254), NINFOM char(254), NTXTDS char(254), PICREP char(254), SCAMAX integer, SCAMIN integer,
      TXTDSC char(254), RECDAT char(254), RECIND char(254), SORDAT char(254), SORIND char(254)
    -> AttributeManager_63
AttributeManager_63
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_14
GeometryFilter_14
    BREAK_AGG = No
    GEOM_PORT_NAMES = Point Area
    POINT -> 3_coastal_hulkes_point (writer POSTGIS_1)
    AREA -> 3_coastal_hulkes_polygon (writer POSTGIS_1)
3_coastal_hulkes_point (writer POSTGIS_1)
    attributes: fidn varchar(20), cathlk varchar(80), colour varchar(80), colpat varchar(80), conrad varchar(80), convis varchar(80), horacc numeric(24,15), horlen numeric(24,15), horwid numeric(24,15), nobjnm varchar(80), objnam varchar(80), veracc numeric(24,15), verlen numeric(24,15), condtn varchar(80), inform varchar(80), ninfom varchar(80), ntxtds varchar(80), picrep varchar(80), scamin numeric(24,15), txtdsc varchar(80), sordat varchar(80), sorind varchar(80)
3_coastal_hulkes_polygon (writer POSTGIS_1)
    attributes: fidn varchar(20), cathlk varchar(80), colour varchar(80), colpat varchar(80), conrad varchar(80), convis varchar(80), horacc numeric(24,15), horlen numeric(24,15), horwid numeric(24,15), nobjnm varchar(80), objnam varchar(80), veracc numeric(24,15), verlen numeric(24,15), condtn varchar(80), inform varchar(80), ninfom varchar(80), ntxtds varchar(80), picrep varchar(80), scamin numeric(24,15), txtdsc varchar(80), sordat varchar(80), sorind varchar(80)
LAKARE (reader S57_1)
    attributes: RCID integer, PRIM integer16, GRUP integer16, OBJL integer, RVER integer16, AGEN integer, FIDN integer, FIDS integer, LNAM char(16), LNAM_REFS{} char(16), FFPT_RIND{} integer16, ELEVAT double, NOBJNM char(254), OBJNAM char(254), VERACC double, VERDAT integer, INFORM char(254), NINFOM char(254), NTXTDS char(254), SCAMAX integer, SCAMIN integer, TXTDSC char(254), RECDAT char(254), RECIND char(254), SORDAT char(254), SORIND char(254)
    -> AttributeManager_30
AttributeManager_30
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_lakare_polygon (writer POSTGIS_1)
3_coastal_lakare_polygon (writer POSTGIS_1)
    attributes: fidn varchar(20), elevat numeric(24,15), nobjnm varchar(80), objnam varchar(80), veracc numeric(24,15), verdat varchar(80), inform varchar(80), ninfom varchar(80), ntxtds varchar(80), scamin numeric(24,15), txtdsc varchar(80), sordat varchar(80), sorind varchar(80)
LIGHTS (reader S57_1)
    attributes: RCID integer, PRIM integer16, GRUP integer16, OBJL integer, RVER integer16, AGEN integer, FIDN integer, FIDS integer, LNAM char(16), LNAM_REFS{} char(16), FFPT_RIND{} integer16, CATLIT char(254), COLOUR char(254), DATEND char(254), DATSTA char(254), EXCLIT integer, HEIGHT double, LITCHR integer, LITVIS char(254), MARSYS integer, MLTYLT integer, NOBJNM char(254), OBJNAM char(254), ORIENT double, PEREND char(254), PERSTA char(254), SECTR1 double, SECTR2 double, SIGGRP char(254), SIGPER double,
      SIGSEQ char(254), STATUS char(254), VERACC double, VALNMR double, VERDAT integer, INFORM char(254), NINFOM char(254), NTXTDS char(254), SCAMAX integer, SCAMIN integer, TXTDSC char(254), RECDAT char(254), RECIND char(254), SORDAT char(254), SORIND char(254)
    -> AttributeManager_9
AttributeManager_9
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> NullAttributeMapper_2
NullAttributeMapper_2
    ATTRCHOICE = Selected Attributes
    ATTRLIST = ORIENT SIGPER
    NULL_TREATMENT = Missing
    SOURCE_ATTR_VAL = Empty
    -> 3_coastal_lights_point (writer POSTGIS_1)
3_coastal_lights_point (writer POSTGIS_1)
    attributes: fidn varchar(20), catlit varchar(80), colour varchar(80), datend varchar(80), datsta varchar(80), exclit varchar(80), height numeric(24,15), litchr varchar(80), litvis varchar(254), marsys varchar(80), mltylt numeric(24,15), nobjnm varchar(80), objnam varchar(80), orient numeric(24,15), perend varchar(80), persta varchar(80), sectr1 numeric(24,15), sectr2 numeric(24,15), siggrp varchar(80), sigper numeric(24,15), sigseq varchar(80), status varchar(80), veracc numeric(24,15), valnmr numeric(24,15), verdat varchar(80), inform varchar(254), ninfom varchar(80), ntxtds varchar(80), scamin numeric(24,15), txtdsc varchar(80),
      sordat varchar(80), sorind varchar(80)
LNDARE (reader S57_1)
    attributes: RCID integer, PRIM integer16, GRUP integer16, OBJL integer, RVER integer16, AGEN integer, FIDN integer, FIDS integer, LNAM char(16), LNAM_REFS{} char(16), FFPT_RIND{} integer16, CONDTN integer, NOBJNM char(254), OBJNAM char(254), STATUS char(254), INFORM char(254), NINFOM char(254), NTXTDS char(254), SCAMAX integer, SCAMIN integer, TXTDSC char(254), RECDAT char(254), RECIND char(254), SORDAT char(254), SORIND char(254)
    -> AttributeManager_10
AttributeManager_10
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter
GeometryFilter
    BREAK_AGG = No
    GEOM_PORT_NAMES = Point Area
    POINT -> 3_coastal_lndare_point (writer POSTGIS_1)
    AREA -> 3_coastal_lndare_polygon (writer POSTGIS_1)
3_coastal_lndare_point (writer POSTGIS_1)
    attributes: fidn varchar(20), condtn varchar(80), nobjnm varchar(80), objnam varchar(80), status varchar(80), inform varchar(80), ninfom varchar(80), ntxtds varchar(80), scamin numeric(24,15), txtdsc varchar(80), sordat varchar(80), sorind varchar(80)
3_coastal_lndare_polygon (writer POSTGIS_1)
    attributes: fidn varchar(20), condtn varchar(80), nobjnm varchar(80), objnam varchar(80), status varchar(80), inform varchar(80), ninfom varchar(80), ntxtds varchar(80), scamin numeric(24,15), txtdsc varchar(80), sordat varchar(80), sorind varchar(80)
LNDELV (reader S57_1)
    attributes: RCID integer, PRIM integer16, GRUP integer16, OBJL integer, RVER integer16, AGEN integer, FIDN integer, FIDS integer, LNAM char(16), LNAM_REFS{} char(16), FFPT_RIND{} integer16, CONVIS integer, ELEVAT double, NOBJNM char(254), OBJNAM char(254), VERACC double, VERDAT integer, INFORM char(254), NINFOM char(254), NTXTDS char(254), SCAMAX integer, SCAMIN integer, TXTDSC char(254), RECDAT char(254), RECIND char(254), SORDAT char(254), SORIND char(254)
    -> AttributeManager_12
AttributeManager_12
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_lndelv_point (writer POSTGIS_1)
3_coastal_lndelv_point (writer POSTGIS_1)
    attributes: fidn varchar(20), convis varchar(80), elevat numeric(24,15), nobjnm varchar(80), objnam varchar(80), veracc numeric(24,15), verdat varchar(80), inform varchar(80), ninfom varchar(80), ntxtds varchar(80), scamin numeric(24,15), txtdsc varchar(80), sordat varchar(80), sorind varchar(80)
LNDMRK (reader S57_1)
    attributes: RCID integer, PRIM integer16, GRUP integer16, OBJL integer, RVER integer16, AGEN integer, FIDN integer, FIDS integer, LNAM char(16), LNAM_REFS{} char(16), FFPT_RIND{} integer16, CATLMK char(254), COLOUR char(254), COLPAT char(254), CONDTN integer, CONRAD integer, CONVIS integer, ELEVAT double, FUNCTN char(254), HEIGHT double, NATCON char(254), NOBJNM char(254), OBJNAM char(254), STATUS char(254), VERACC double, VERDAT integer, VERLEN double, INFORM char(254), NINFOM char(254), NTXTDS char(254),
      PICREP char(254), SCAMAX integer, SCAMIN integer, TXTDSC char(254), RECDAT char(254), RECIND char(254), SORDAT char(254), SORIND char(254)
    -> AttributeManager_13
AttributeManager_13
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE PICREP
      REMOVE SCAMAX
      REMOVE RECDAT
      REMOVE RECIND
      REMOVE DSNM
    -> 3_coastal_lndmrk_point (writer POSTGIS_1)
3_coastal_lndmrk_point (writer POSTGIS_1)
    attributes: fidn varchar(20), catlmk varchar(80), colour varchar(80), colpat varchar(80), condtn varchar(80), conrad varchar(80), convis varchar(80), elevat numeric(24,15), functn varchar(80), height numeric(24,15), natcon varchar(80), nobjnm varchar(80), objnam varchar(80), status varchar(80), veracc numeric(24,15), verdat varchar(80), verlen numeric(24,15), inform varchar(254), ninfom varchar(80), ntxtds varchar(80), scamin numeric(24,15), txtdsc varchar(80), sordat varchar(80), sorind varchar(80)
LNDRGN (reader S57_1)
    attributes: RCID integer, PRIM integer16, GRUP integer16, OBJL integer, RVER integer16, AGEN integer, FIDN integer, FIDS integer, LNAM char(16), LNAM_REFS{} char(16), FFPT_RIND{} integer16, CATLND char(254), NATQUA char(254), NATSUR char(254), NOBJNM char(254), OBJNAM char(254), WATLEV integer, INFORM char(254), NINFOM char(254), NTXTDS char(254), SCAMAX integer, SCAMIN integer, TXTDSC char(254), RECDAT char(254), RECIND char(254), SORDAT char(254), SORIND char(254)
    -> AttributeManager_14
AttributeManager_14
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_3
GeometryFilter_3
    BREAK_AGG = No
    GEOM_PORT_NAMES = Point Area
    POINT -> 3_coastal_lndrgn_point (writer POSTGIS_1)
    AREA -> 3_coastal_lndrgn_polygon (writer POSTGIS_1)
3_coastal_lndrgn_point (writer POSTGIS_1)
    attributes: fidn varchar(20), catlnd varchar(80), natqua varchar(80), natsur varchar(80), nobjnm varchar(80), objnam varchar(80), watlev varchar(80), inform varchar(80), ninfom varchar(80), ntxtds varchar(80), scamin numeric(24,15), txtdsc varchar(80), sordat varchar(80), sorind varchar(80)
3_coastal_lndrgn_polygon (writer POSTGIS_1)
    attributes: fidn varchar(20), catlnd varchar(80), natqua varchar(80), natsur varchar(80), nobjnm varchar(80), objnam varchar(80), watlev varchar(80), inform varchar(80), ninfom varchar(80), ntxtds varchar(80), scamin numeric(24,15), txtdsc varchar(80), sordat varchar(80), sorind varchar(80)
LOCMAG (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), VALLMA double, INFORM char(254), NINFOM char(254), NTXTDS char(254), SCAMAX integer, SCAMIN integer, TXTDSC char(254), RECDAT char(254), RECIND char(254), SORDAT char(254), SORIND char(254)
    -> AttributeManager_64
AttributeManager_64
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_15
GeometryFilter_15
    BREAK_AGG = No
    GEOM_PORT_NAMES = Point Area
    POINT -> NullAttributeMapper_12
    AREA -> NullAttributeMapper_14
NullAttributeMapper_12
    ATTRCHOICE = Selected Attributes
    ATTRLIST = VALLMA
    NULL_TREATMENT = Missing
    SOURCE_ATTR_VAL = Empty
    -> 3_coastal_locmag_point (writer POSTGIS_1)
3_coastal_locmag_point (writer POSTGIS_1)
    attributes: fidn varchar(20), nobjnm varchar(80), objnam varchar(80), vallma numeric(24,15), inform varchar(254), ninfom varchar(80), ntxtds varchar(80), scamin numeric(24,15), txtdsc varchar(80), sordat varchar(80), sorind varchar(80)
NullAttributeMapper_14
    ATTRCHOICE = Selected Attributes
    ATTRLIST = VALLMA
    NULL_TREATMENT = Missing
    SOURCE_ATTR_VAL = Empty
    -> 3_coastal_locmag_polygon (writer POSTGIS_1)
3_coastal_locmag_polygon (writer POSTGIS_1)
    attributes: fidn varchar(20), nobjnm varchar(80), objnam varchar(80), vallma numeric(24,15), inform varchar(254), ninfom varchar(80), ntxtds varchar(80), scamin numeric(24,15), txtdsc varchar(80), sordat varchar(80), sorind varchar(80)
M_COVR (reader S57_1)
    attributes: RCID integer, PRIM integer16, GRUP integer16, OBJL integer, RVER integer16, AGEN integer, FIDN integer, FIDS integer, LNAM char(16), LNAM_REFS{} char(16), FFPT_RIND{} integer16, CATCOV integer, INFORM char(254), NINFOM char(254), RECDAT char(254), RECIND char(254), SORDAT char(254), SORIND char(254)
    -> AttributeManager_15
AttributeManager_15
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
      REMOVE DSNM
    -> 3_coastal_m_covr_polygon (writer POSTGIS_1)
3_coastal_m_covr_polygon (writer POSTGIS_1)
    attributes: fidn varchar(20), catcov varchar(80), inform varchar(254), ninfom varchar(80), sordat varchar(80), sorind varchar(80)
M_NPUB (reader S57_1)
    attributes: RCID integer, PRIM integer16, GRUP integer16, OBJL integer, RVER integer16, AGEN integer, FIDN integer, FIDS integer, LNAM char(16), LNAM_REFS{} char(16), FFPT_RIND{} integer16, INFORM char(254), NINFOM char(254), NTXTDS char(254), PICREP char(254), PUBREF char(254), TXTDSC char(254), RECDAT char(254), RECIND char(254), SORDAT char(254), SORIND char(254)
    -> AttributeManager_16
AttributeManager_16
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
      REMOVE DSNM
    -> 3_coastal_m_npub_polygon (writer POSTGIS_1)
3_coastal_m_npub_polygon (writer POSTGIS_1)
    attributes: fidn varchar(20), inform varchar(80), ninfom varchar(80), ntxtds varchar(80), picrep varchar(80), pubref varchar(80), txtdsc varchar(80), sordat varchar(80), sorind varchar(80)
M_NSYS (reader S57_1)
    attributes: RCID integer, PRIM integer16, GRUP integer16, OBJL integer, RVER integer16, AGEN integer, FIDN integer, FIDS integer, LNAM char(16), LNAM_REFS{} char(16), FFPT_RIND{} integer16, MARSYS integer, ORIENT double, INFORM char(254), NINFOM char(254), NTXTDS char(254), SCAMAX integer, SCAMIN integer, TXTDSC char(254), RECDAT char(254), RECIND char(254), SORDAT char(254), SORIND char(254)
    -> AttributeManager_17
AttributeManager_17
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_m_nsys_polygon (writer POSTGIS_1)
3_coastal_m_nsys_polygon (writer POSTGIS_1)
    attributes: fidn varchar(20), marsys varchar(80), orient numeric(24,15), inform varchar(80), ninfom varchar(80), ntxtds varchar(80), scamin numeric(24,15), txtdsc varchar(80), sordat varchar(80), sorind varchar(80)
M_QUAL (reader S57_1)
    attributes: RCID integer, PRIM integer16, GRUP integer16, OBJL integer, RVER integer16, AGEN integer, FIDN integer, FIDS integer, LNAM char(16), LNAM_REFS{} char(16), FFPT_RIND{} integer16, CATQUA integer, CATZOC integer, DRVAL1 double, DRVAL2 double, POSACC double, SOUACC double, SUREND char(254), SURSTA char(254), TECSOU char(254), VERDAT integer, INFORM char(254), NINFOM char(254), NTXTDS char(254), TXTDSC char(254), RECDAT char(254), RECIND char(254), SORDAT char(254), SORIND char(254)
    -> AttributeManager_18
AttributeManager_18
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
      REMOVE DSNM
    -> 3_coastal_m_qual_polygon (writer POSTGIS_1)
3_coastal_m_qual_polygon (writer POSTGIS_1)
    attributes: fidn varchar(20), catqua varchar(80), catzoc varchar(80), drval1 numeric(24,15), drval2 numeric(24,15), posacc numeric(24,15), souacc numeric(24,15), surend varchar(80), sursta varchar(80), tecsou varchar(80), verdat varchar(80), inform varchar(254), ninfom varchar(80), ntxtds varchar(80), txtdsc varchar(80), sordat varchar(80), sorind varchar(254)
MAGVAR (reader S57_1)
    attributes: RCID integer, PRIM integer16, GRUP integer16, OBJL integer, RVER integer16, AGEN integer, FIDN integer, FIDS integer, LNAM char(16), LNAM_REFS{} char(16), FFPT_RIND{} integer16, DATEND char(254), DATSTA char(254), RYRMGV char(254), VALACM double, VALMAG double, INFORM char(254), NINFOM char(254), SCAMAX integer, SCAMIN integer, RECDAT char(254), RECIND char(254), SORDAT char(254), SORIND char(254)
    -> AttributeManager_19
AttributeManager_19
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_16
GeometryFilter_16
    BREAK_AGG = No
    GEOM_PORT_NAMES = Point Area
    POINT -> 3_coastal_magvar_point (writer POSTGIS_1)
    AREA -> 3_coastal_magvar_polygon (writer POSTGIS_1)
3_coastal_magvar_point (writer POSTGIS_1)
    attributes: fidn varchar(20), datend varchar(80), datsta varchar(80), ryrmgv varchar(80), valacm numeric(24,15), valmag numeric(24,15), inform varchar(254), ninfom varchar(80), scamin numeric(24,15), sordat varchar(80), sorind varchar(80)
3_coastal_magvar_polygon (writer POSTGIS_1)
    attributes: fidn varchar(20), datend varchar(80), datsta varchar(80), ryrmgv varchar(80), valacm numeric(24,15), valmag numeric(24,15), inform varchar(254), ninfom varchar(80), scamin numeric(24,15), sordat varchar(80), sorind varchar(80)
MARCUL (reader S57_1)
    attributes: RCID integer, PRIM integer16, GRUP integer16, OBJL integer, RVER integer16, AGEN integer, FIDN integer, FIDS integer, LNAM char(16), LNAM_REFS{} char(16), FFPT_RIND{} integer16, CATMFA integer, DATEND char(254), DATSTA char(254), EXPSOU integer, NOBJNM char(254), OBJNAM char(254), PEREND char(254), PERSTA char(254), QUASOU char(254), RESTRN char(254), SOUACC double, STATUS char(254), VALSOU double, VERACC double, VERDAT integer, VERLEN double, WATLEV integer, INFORM char(254), NINFOM char(254),
      NTXTDS char(254), SCAMAX integer, SCAMIN integer, TXTDSC char(254), RECDAT char(254), RECIND char(254), SORDAT char(254), SORIND char(254)
    -> AttributeManager_65
AttributeManager_65
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_17
GeometryFilter_17
    BREAK_AGG = No
    GEOM_PORT_NAMES = Point Area
    POINT -> NullAttributeMapper_11
    AREA -> NullAttributeMapper_17
NullAttributeMapper_11
    ATTRCHOICE = Selected Attributes
    ATTRLIST = VALSOU
    NULL_TREATMENT = Missing
    SOURCE_ATTR_VAL = Empty
    -> 3_coastal_marcul_point (writer POSTGIS_1)
3_coastal_marcul_point (writer POSTGIS_1)
    attributes: fidn varchar(20), catmfa varchar(80), datend varchar(80), datsta varchar(80), expsou varchar(80), nobjnm varchar(80), objnam varchar(80), perend varchar(80), persta varchar(80), quasou varchar(80), restrn varchar(80), souacc numeric(24,15), status varchar(80), valsou numeric(24,15), veracc numeric(24,15), verdat varchar(80), verlen numeric(24,15), watlev varchar(80), inform varchar(254), ninfom varchar(80), ntxtds varchar(80), scamin numeric(24,15), txtdsc varchar(80), sordat varchar(80), sorind varchar(80)
NullAttributeMapper_17
    ATTRCHOICE = Selected Attributes
    ATTRLIST = VALSOU
    NULL_TREATMENT = Missing
    SOURCE_ATTR_VAL = Empty
    -> 3_coastal_marcul_polygon (writer POSTGIS_1)
3_coastal_marcul_polygon (writer POSTGIS_1)
    attributes: fidn varchar(20), catmfa varchar(80), datend varchar(80), datsta varchar(80), expsou varchar(80), nobjnm varchar(80), objnam varchar(80), perend varchar(80), persta varchar(80), quasou varchar(80), restrn varchar(80), souacc numeric(24,15), status varchar(80), valsou numeric(24,15), veracc numeric(24,15), verdat varchar(80), verlen numeric(24,15), watlev varchar(80), inform varchar(254), ninfom varchar(80), ntxtds varchar(80), scamin numeric(24,15), txtdsc varchar(80), sordat varchar(80), sorind varchar(80)
MORFAC (reader S57_1)
    attributes: RCID integer, PRIM integer16, GRUP integer16, OBJL integer, RVER integer16, AGEN integer, FIDN integer, FIDS integer, LNAM char(16), LNAM_REFS{} char(16), FFPT_RIND{} integer16, BOYSHP integer, CATMOR integer, COLOUR char(254), COLPAT char(254), CONDTN integer, CONRAD integer, CONVIS integer, DATEND char(254), DATSTA char(254), HEIGHT double, NATCON char(254), NOBJNM char(254), OBJNAM char(254), PEREND char(254), PERSTA char(254), STATUS char(254), VERACC double, VERDAT integer, VERLEN double,
      WATLEV integer, INFORM char(254), NINFOM char(254), NTXTDS char(254), PICREP char(254), SCAMAX integer, SCAMIN integer, TXTDSC char(254), RECDAT char(254), RECIND char(254), SORDAT char(254), SORIND char(254)
    -> AttributeManager_66
AttributeManager_66
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_morfac_point (writer POSTGIS_1)
3_coastal_morfac_point (writer POSTGIS_1)
    attributes: fidn varchar(20), boyshp varchar(80), catmor varchar(80), colour varchar(80), colpat varchar(80), condtn varchar(80), conrad varchar(80), convis varchar(80), datend varchar(80), datsta varchar(80), height numeric(24,15), natcon varchar(80), nobjnm varchar(80), objnam varchar(80), perend varchar(80), persta varchar(80), status varchar(80), veracc numeric(24,15), verdat varchar(80), verlen numeric(24,15), watlev varchar(80), inform varchar(254), ninfom varchar(80), ntxtds varchar(80), picrep varchar(80), scamin numeric(24,15), txtdsc varchar(80), sordat varchar(80), sorind varchar(80)
NAVLNE (reader S57_1)
    attributes: RCID integer, PRIM integer16, GRUP integer16, OBJL integer, RVER integer16, AGEN integer, FIDN integer, FIDS integer, LNAM char(16), LNAM_REFS{} char(16), FFPT_RIND{} integer16, CATNAV integer, DATEND char(254), DATSTA char(254), ORIENT double, PEREND char(254), PERSTA char(254), STATUS char(254), INFORM char(254), NINFOM char(254), NTXTDS char(254), SCAMAX integer, SCAMIN integer, TXTDSC char(254), RECDAT char(254), RECIND char(254), SORDAT char(254), SORIND char(254)
    -> AttributeManager_67
AttributeManager_67
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_navlne_arc (writer POSTGIS_1)
3_coastal_navlne_arc (writer POSTGIS_1)
    attributes: fidn varchar(20), catnav varchar(80), datend varchar(80), datsta varchar(80), orient numeric(24,15), perend varchar(80), persta varchar(80), status varchar(80), inform varchar(254), ninfom varchar(80), ntxtds varchar(80), scamin numeric(24,15), txtdsc varchar(80), sordat varchar(80), sorind varchar(80)
OBSTRN (reader S57_1)
    attributes: RCID integer, PRIM integer16, GRUP integer16, OBJL integer, RVER integer16, AGEN integer, FIDN integer, FIDS integer, LNAM char(16), LNAM_REFS{} char(16), FFPT_RIND{} integer16, CATOBS integer, CONDTN integer, EXPSOU integer, HEIGHT double, NATCON char(254), NATQUA char(254), NOBJNM char(254), OBJNAM char(254), PRODCT char(254), QUASOU char(254), SOUACC double, STATUS char(254), TECSOU char(254), VALSOU double, VERACC double, VERDAT integer, VERLEN double, WATLEV integer, NATSUR char(254),
      INFORM char(254), NINFOM char(254), NTXTDS char(254), SCAMAX integer, SCAMIN integer, TXTDSC char(254), RECDAT char(254), RECIND char(254), SORDAT char(254), SORIND char(254)
    -> AttributeManager_20
AttributeManager_20
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_4
GeometryFilter_4
    BREAK_AGG = No
    GEOM_PORT_NAMES = Point Area
    POINT -> NullAttributeMapper_5
    AREA -> NullAttributeMapper_4
NullAttributeMapper_5
    ATTRCHOICE = Selected Attributes
    ATTRLIST = VALSOU
    NULL_TREATMENT = Missing
    SOURCE_ATTR_VAL = Empty
    -> 3_coastal_obstrn_point (writer POSTGIS_1)
3_coastal_obstrn_point (writer POSTGIS_1)
    attributes: fidn varchar(20), catobs varchar(80), condtn varchar(80), expsou varchar(80), height numeric(24,15), natcon varchar(80), natqua varchar(80), nobjnm varchar(80), objnam varchar(80), prodct varchar(80), quasou varchar(80), souacc numeric(24,15), status varchar(80), tecsou varchar(80), valsou numeric(24,15), veracc numeric(24,15), verdat varchar(80), verlen numeric(24,15), watlev varchar(80), natsur varchar(80), inform varchar(254), ninfom varchar(78), ntxtds varchar(80), scamin numeric(24,15), txtdsc varchar(80), sordat varchar(80), sorind varchar(80)
NullAttributeMapper_4
    ATTRCHOICE = Selected Attributes
    ATTRLIST = VALSOU
    NULL_TREATMENT = Missing
    SOURCE_ATTR_VAL = Empty
    -> 3_coastal_obstrn_polygon (writer POSTGIS_1)
3_coastal_obstrn_polygon (writer POSTGIS_1)
    attributes: fidn varchar(20), catobs varchar(80), condtn varchar(80), expsou varchar(80), height numeric(24,15), natcon varchar(80), natqua varchar(80), nobjnm varchar(80), objnam varchar(80), prodct varchar(80), quasou varchar(80), souacc numeric(24,15), status varchar(80), tecsou varchar(80), valsou numeric(20,15), veracc numeric(24,15), verdat varchar(80), verlen numeric(80,15), watlev varchar(20), natsur varchar(80), inform varchar(254), ninfom varchar(80), ntxtds varchar(80), scamin numeric(24,15), txtdsc varchar(80), sordat varchar(80), sorind varchar(80)
OFSPLF (reader S57_1)
    attributes: RCID integer, PRIM integer16, GRUP integer16, OBJL integer, RVER integer16, AGEN integer, FIDN integer, FIDS integer, LNAM char(16), LNAM_REFS{} char(16), FFPT_RIND{} integer16, CATOFP char(254), COLOUR char(254), COLPAT char(254), CONDTN integer, CONRAD integer, CONVIS integer, DATEND char(254), DATSTA char(254), HEIGHT double, NATCON char(254), NOBJNM char(254), OBJNAM char(254), PRODCT char(254), STATUS char(254), VERACC double, VERDAT integer, VERLEN double, INFORM char(254), NINFOM char(254),
      NTXTDS char(254), PICREP char(254), SCAMAX integer, SCAMIN integer, TXTDSC char(254), RECDAT char(254), RECIND char(254), SORDAT char(254), SORIND char(254)
    -> AttributeManager_31
AttributeManager_31
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_ofsplf_point (writer POSTGIS_1)
3_coastal_ofsplf_point (writer POSTGIS_1)
    attributes: fidn varchar(20), catofp varchar(80), colour varchar(80), colpat varchar(80), condtn varchar(80), conrad varchar(80), convis varchar(80), datend varchar(80), datsta varchar(80), height numeric(24,15), natcon varchar(80), nobjnm varchar(80), objnam varchar(80), prodct varchar(80), status varchar(80), veracc numeric(24,15), verdat varchar(80), verlen numeric(24,15), inform varchar(254), ninfom varchar(80), ntxtds varchar(80), picrep varchar(80), scamin numeric(24,12), txtdsc varchar(80), sordat varchar(80), sorind varchar(80)
PILBOP (reader S57_1)
    attributes: RCID integer, PRIM integer16, GRUP integer16, OBJL integer, RVER integer16, AGEN integer, FIDN integer, FIDS integer, LNAM char(16), LNAM_REFS{} char(16), FFPT_RIND{} integer16, CATPIL integer, COMCHA char(254), DATEND char(254), DATSTA char(254), NOBJNM char(254), NPLDST char(254), OBJNAM char(254), PEREND char(254), PERSTA char(254), PILDST char(254), STATUS char(254), INFORM char(254), NINFOM char(254), NTXTDS char(254), SCAMAX integer, SCAMIN integer, TXTDSC char(254), RECDAT char(254), RECIND char(254),
      SORDAT char(254), SORIND char(254)
    -> AttributeManager_32
AttributeManager_32
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_pilbop_point (writer POSTGIS_1)
3_coastal_pilbop_point (writer POSTGIS_1)
    attributes: fidn varchar(20), catpil varchar(80), comcha varchar(80), datend varchar(80), datsta varchar(80), nobjnm varchar(80), npldst varchar(80), objnam varchar(80), status varchar(80), inform varchar(254), ninfom varchar(80), ntxtds varchar(80), scamin numeric(24,15), txtdsc varchar(80), sordat varchar(80), sorind varchar(80), perend varchar(80), persta varchar(80), pildst varchar(80)
PILPNT (reader S57_1)
    attributes: RCID integer, PRIM integer16, GRUP integer16, OBJL integer, RVER integer16, AGEN integer, FIDN integer, FIDS integer, LNAM char(16), LNAM_REFS{} char(16), FFPT_RIND{} integer16, CATPLE integer, COLOUR char(254), COLPAT char(254), CONDTN integer, CONVIS integer, DATEND char(254), DATSTA char(254), HEIGHT double, NOBJNM char(254), OBJNAM char(254), VERACC double, VERDAT integer, VERLEN double, INFORM char(254), NINFOM char(254), NTXTDS char(254), SCAMAX integer, SCAMIN integer, TXTDSC char(254),
      RECDAT char(254), RECIND char(254), SORDAT char(254), SORIND char(254)
    -> AttributeManager_68
AttributeManager_68
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_pilpnt_point (writer POSTGIS_1)
3_coastal_pilpnt_point (writer POSTGIS_1)
    attributes: fidn varchar(20), catple varchar(80), colour varchar(80), colpat varchar(80), condtn varchar(80), convis varchar(80), datend varchar(80), datsta varchar(80), height numeric(24,15), nobjnm varchar(80), objnam varchar(80), veracc numeric(24,15), verdat varchar(80), verlen numeric(24,15), inform varchar(254), ninfom varchar(80), ntxtds varchar(80), scamin numeric(24,15), txtdsc varchar(80), sordat varchar(80), sorind varchar(80)
PIPSOL (reader S57_1)
    attributes: RCID integer, PRIM integer16, GRUP integer16, OBJL integer, RVER integer16, AGEN integer, FIDN integer, FIDS integer, LNAM char(16), LNAM_REFS{} char(16), FFPT_RIND{} integer16, BURDEP double, CATPIP char(254), CONDTN integer, DATEND char(254), DATSTA char(254), DRVAL1 double, DRVAL2 double, NOBJNM char(254), OBJNAM char(254), PRODCT char(254), STATUS char(254), VERACC double, VERLEN double, VERDAT integer, INFORM char(254), NINFOM char(254), NTXTDS char(254), SCAMAX integer, SCAMIN integer,
      TXTDSC char(254), RECDAT char(254), RECIND char(254), SORDAT char(254), SORIND char(254)
    -> AttributeManager_69
AttributeManager_69
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_pipsol_arc (writer POSTGIS_1)
3_coastal_pipsol_arc (writer POSTGIS_1)
    attributes: fidn varchar(20), burdep numeric(24,15), catpip varchar(80), condtn varchar(80), datend varchar(80), datsta varchar(80), drval1 numeric(24,15), drval2 numeric(24,15), nobjnm varchar(80), objnam varchar(80), prodct varchar(80), status varchar(80), veracc numeric(24,15), verlen numeric(24,15), verdat varchar(80), inform varchar(254), ninfom varchar(80), ntxtds varchar(80), scamin numeric(24,15), txtdsc varchar(80), sordat varchar(80), sorind varchar(80)
PRCARE (reader S57_1)
    attributes: RCID integer, PRIM integer16, GRUP integer16, OBJL integer, RVER integer16, AGEN integer, FIDN integer, FIDS integer, LNAM char(16), LNAM_REFS{} char(16), FFPT_RIND{} integer16, DATEND char(254), DATSTA char(254), RESTRN char(254), STATUS char(254), INFORM char(254), NINFOM char(254), NTXTDS char(254), SCAMAX integer, SCAMIN integer, TXTDSC char(254), RECDAT char(254), RECIND char(254), SORDAT char(254), SORIND char(254)
    -> AttributeManager_33
AttributeManager_33
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_prcare_polygon (writer POSTGIS_1)
3_coastal_prcare_polygon (writer POSTGIS_1)
    attributes: fidn varchar(20), datend varchar(80), datsta varchar(80), restrn varchar(80), status varchar(80), inform varchar(254), ninfom varchar(80), ntxtds varchar(80), scamin numeric(24,15), txtdsc varchar(80), sordat varchar(80), sorind varchar(80)
RDOCAL (reader S57_1)
    attributes: RCID integer, PRIM integer16, GRUP integer16, OBJL integer, RVER integer16, AGEN integer, FIDN integer, FIDS integer, LNAM char(16), LNAM_REFS{} char(16), FFPT_RIND{} integer16, COMCHA char(254), DATEND char(254), DATSTA char(254), NOBJNM char(254), OBJNAM char(254), ORIENT double, PEREND char(254), PERSTA char(254), STATUS char(254), TRAFIC integer, INFORM char(254), NINFOM char(254), NTXTDS char(254), SCAMAX integer, SCAMIN integer, TXTDSC char(254), RECDAT char(254), RECIND char(254), SORDAT char(254),
      SORIND char(254)
    -> AttributeManager_22
AttributeManager_22
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_18
GeometryFilter_18
    BREAK_AGG = No
    GEOM_PORT_NAMES = Point Line
    POINT -> 3_coastal_rdocal_point (writer POSTGIS_1)
    LINE -> 3_coastal_rdocal_arc (writer POSTGIS_1)
3_coastal_rdocal_point (writer POSTGIS_1)
    attributes: fidn varchar(20), comcha varchar(80), datend varchar(80), datsta varchar(80), nobjnm varchar(80), objnam varchar(80), orient numeric(24,15), perend varchar(80), persta varchar(80), status varchar(80), trafic varchar(80), inform varchar(254), ninfom varchar(80), ntxtds varchar(80), scamin numeric(24,15), txtdsc varchar(80), sordat varchar(80), sorind varchar(80)
3_coastal_rdocal_arc (writer POSTGIS_1)
    attributes: fidn varchar(20), comcha varchar(80), datend varchar(80), datsta varchar(80), nobjnm varchar(80), objnam varchar(80), orient numeric(24,15), perend varchar(80), persta varchar(80), status varchar(80), trafic varchar(80), inform varchar(254), ninfom varchar(80), ntxtds varchar(80), scamin numeric(24,15), txtdsc varchar(80), sordat varchar(80), sorind varchar(80)
RECTRC (reader S57_1)
    attributes: RCID integer, PRIM integer16, GRUP integer16, OBJL integer, RVER integer16, AGEN integer, FIDN integer, FIDS integer, LNAM char(16), LNAM_REFS{} char(16), FFPT_RIND{} integer16, CATTRK integer, DATEND char(254), DATSTA char(254), DRVAL1 double, DRVAL2 double, NOBJNM char(254), OBJNAM char(254), ORIENT double, PEREND char(254), PERSTA char(254), QUASOU char(254), SOUACC double, STATUS char(254), TECSOU char(254), TRAFIC integer, VERDAT integer, INFORM char(254), NINFOM char(254), NTXTDS char(254),
      SCAMAX integer, SCAMIN integer, TXTDSC char(254), RECDAT char(254), RECIND char(254), SORDAT char(254), SORIND char(254)
    -> AttributeManager_70
AttributeManager_70
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_rectrc_arc (writer POSTGIS_1)
3_coastal_rectrc_arc (writer POSTGIS_1)
    attributes: fidn varchar(20), cattrk varchar(80), datend varchar(80), datsta varchar(80), drval1 numeric(24,15), drval2 numeric(24,15), nobjnm varchar(80), objnam varchar(80), orient numeric(24,15), perend varchar(80), persta varchar(80), quasou varchar(80), souacc numeric(24,15), status varchar(80), tecsou varchar(80), trafic varchar(80), verdat varchar(80), inform varchar(254), ninfom varchar(80), ntxtds varchar(80), scamin numeric(24,15), txtdsc varchar(80), sordat varchar(80), sorind varchar(80)
RESARE (reader S57_1)
    attributes: RCID integer, PRIM integer16, GRUP integer16, OBJL integer, RVER integer16, AGEN integer, FIDN integer, FIDS integer, LNAM char(16), LNAM_REFS{} char(16), FFPT_RIND{} integer16, CATREA char(254), DATEND char(254), DATSTA char(254), NOBJNM char(254), OBJNAM char(254), PEREND char(254), PERSTA char(254), RESTRN char(254), STATUS char(254), INFORM char(254), NINFOM char(254), NTXTDS char(254), SCAMAX integer, SCAMIN integer, TXTDSC char(254), RECDAT char(254), RECIND char(254), SORDAT char(254), SORIND char(254)
    -> AttributeManager_34
AttributeManager_34
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_resare_polygon (writer POSTGIS_1)
3_coastal_resare_polygon (writer POSTGIS_1)
    attributes: fidn varchar(20), catrea varchar(80), datend varchar(80), datsta varchar(80), nobjnm varchar(80), objnam varchar(80), perend varchar(80), persta varchar(80), restrn varchar(80), status varchar(80), inform varchar(254), ninfom varchar(80), ntxtds varchar(80), scamin numeric(24,15), txtdsc varchar(80), sordat varchar(80), sorind varchar(80)
RIVERS (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), STATUS char(254), INFORM char(254), NINFOM char(254), NTXTDS char(254), SCAMAX integer, SCAMIN integer, TXTDSC char(254), RECDAT char(254), RECIND char(254), SORDAT char(254), SORIND char(254)
    -> AttributeManager_35
AttributeManager_35
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_19
GeometryFilter_19
    BREAK_AGG = No
    GEOM_PORT_NAMES = Area Line
    AREA -> 3_coastal_rivers_polygon (writer POSTGIS_1)
    LINE -> 3_coastal_rivers_arc (writer POSTGIS_1)
3_coastal_rivers_polygon (writer POSTGIS_1)
    attributes: fidn varchar(20), nobjnm varchar(80), objnam varchar(80), status varchar(80), inform varchar(80), ninfom varchar(80), ntxtds varchar(80), scamin numeric(24,15), txtdsc varchar(80), sordat varchar(80), sorind varchar(80)
3_coastal_rivers_arc (writer POSTGIS_1)
    attributes: fidn varchar(20), nobjnm varchar(80), objnam varchar(80), status varchar(80), inform varchar(254), ninfom varchar(80), ntxtds varchar(80), scamin numeric(24,15), txtdsc varchar(80), sordat varchar(80), sorind varchar(80)
RTPBCN (reader S57_1)
    attributes: RCID integer, PRIM integer16, GRUP integer16, OBJL integer, RVER integer16, AGEN integer, FIDN integer, FIDS integer, LNAM char(16), LNAM_REFS{} char(16), FFPT_RIND{} integer16, CATRTB integer, DATEND char(254), DATSTA char(254), NOBJNM char(254), OBJNAM char(254), RADWAL char(254), SECTR1 double, SECTR2 double, SIGGRP char(254), SIGSEQ char(254), STATUS char(254), VALMXR double, INFORM char(254), NINFOM char(254), NTXTDS char(254), SCAMAX integer, SCAMIN integer, TXTDSC char(254), RECDAT char(254),
      RECIND char(254), SORDAT char(254), SORIND char(254)
    -> AttributeManager_36
AttributeManager_36
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> 3_coastal_rtpbcn_point (writer POSTGIS_1)
3_coastal_rtpbcn_point (writer POSTGIS_1)
    attributes: fidn varchar(20), catrtb varchar(80), datend varchar(80), datsta varchar(80), nobjnm varchar(80), objnam varchar(80), radwal varchar(80), sectr1 numeric(24,15), sectr2 numeric(24,15), siggrp varchar(80), sigseq varchar(80), status varchar(80), valmxr numeric(24,15), inform varchar(254), ninfom varchar(80), ntxtds varchar(80), scamin numeric(24,15), txtdsc varchar(80), sordat varchar(80), sorind varchar(80)
SBDARE (reader S57_1)
    attributes: RCID integer, PRIM integer16, GRUP integer16, OBJL integer, RVER integer16, AGEN integer, FIDN integer, FIDS integer, LNAM char(16), LNAM_REFS{} char(16), FFPT_RIND{} integer16, COLOUR char(254), NATQUA char(254), NATSUR char(254), WATLEV integer, OBJNAM char(254), NOBJNM char(254), INFORM char(254), NINFOM char(254), NTXTDS char(254), SCAMAX integer, SCAMIN integer, TXTDSC char(254), RECDAT char(254), RECIND char(254), SORDAT char(254), SORIND char(254)
    -> AttributeManager_23
AttributeManager_23
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_5
GeometryFilter_5
    BREAK_AGG = No
    GEOM_PORT_NAMES = Point Area
    POINT -> 3_coastal_sbdare_point (writer POSTGIS_1)
    AREA -> 3_coastal_sbdare_polygon (writer POSTGIS_1)
3_coastal_sbdare_point (writer POSTGIS_1)
    attributes: fidn varchar(20), colour varchar(80), natqua varchar(80), natsur varchar(80), watlev varchar(80), objnam varchar(80), nobjnm varchar(80), inform varchar(254), ninfom varchar(80), ntxtds varchar(80), scamin numeric(24,15), txtdsc varchar(80), sordat varchar(80), sorind varchar(80)
3_coastal_sbdare_polygon (writer POSTGIS_1)
    attributes: fidn varchar(20), colour varchar(80), natqua varchar(80), natsur varchar(80), watlev varchar(80), objnam varchar(80), nobjnm varchar(80), inform varchar(254), ninfom varchar(80), ntxtds varchar(80), scamin numeric(24,15), txtdsc varchar(80), sordat varchar(80), sorind varchar(80)
SEAARE (reader S57_1)
    attributes: RCID integer, PRIM integer16, GRUP integer16, OBJL integer, RVER integer16, AGEN integer, FIDN integer, FIDS integer, LNAM char(16), LNAM_REFS{} char(16), FFPT_RIND{} integer16, CATSEA integer, NOBJNM char(254), OBJNAM char(254), INFORM char(254), NINFOM char(254), NTXTDS char(254), SCAMAX integer, SCAMIN integer, TXTDSC char(254), RECDAT char(254), RECIND char(254), SORDAT char(254), SORIND char(254)
    -> AttributeManager_11
AttributeManager_11
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_6
GeometryFilter_6
    BREAK_AGG = No
    GEOM_PORT_NAMES = Point Area
    POINT -> 3_coastal_seaare_point (writer POSTGIS_1)
    AREA -> 3_coastal_seaare_polygon (writer POSTGIS_1)
3_coastal_seaare_point (writer POSTGIS_1)
    attributes: fidn varchar(20), catsea varchar(80), nobjnm varchar(80), objnam varchar(80), inform varchar(254), ninfom varchar(80), ntxtds varchar(80), scamin numeric(24,15), txtdsc varchar(80), sordat varchar(80), sorind varchar(80)
3_coastal_seaare_polygon (writer POSTGIS_1)
    attributes: fidn varchar(20), catsea varchar(80), nobjnm varchar(80), objnam varchar(80), inform varchar(254), ninfom varchar(80), ntxtds varchar(80), scamin numeric(24,15), txtdsc varchar(80), sordat varchar(80), sorind varchar(80)
SILTNK (reader S57_1)
    attributes: RCID integer, PRIM integer16, GRUP integer16, OBJL integer, RVER integer16, AGEN integer, FIDN integer, FIDS integer, LNAM char(16), LNAM_REFS{} char(16), FFPT_RIND{} integer16, BUISHP integer, CATSIL integer, COLOUR char(254), COLPAT char(254), CONDTN integer, CONRAD integer, CONVIS integer, ELEVAT double, HEIGHT double, NATCON char(254), NOBJNM char(254), OBJNAM char(254), PRODCT char(254), STATUS char(254), VERACC double, VERDAT integer, VERLEN double, INFORM char(254), NINFOM char(254),
      NTXTDS char(254), PICREP char(254), SCAMAX integer, SCAMIN integer, TXTDSC char(254), RECDAT char(254), RECIND char(254), SORDAT char(254), SORIND char(254)
    -> AttributeManager_71
AttributeManager_71
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE DSNM
    -> GeometryFilter_20
GeometryFilter_20
    BREAK_AGG = No
    GEOM_PORT_NAMES = Point Area
    POINT -> 3_coastal_siltnk_point (writer POSTGIS_1)
    AREA -> 3_coastal_siltnk_polygon (writer POSTGIS_1)
3_coastal_siltnk_point (writer POSTGIS_1)
    attributes: fidn varchar(20), buishp varchar(80), catsil varchar(80), colour varchar(80), colpat varchar(80), condtn varchar(80), conrad varchar(80), convis varchar(80), elevat numeric(24,15), height numeric(24,15), natcon varchar(80), nobjnm varchar(80), objnam varchar(80), prodct varchar(80), status varchar(80), veracc numeric(24,15), verdat varchar(80), verlen numeric(24,15), inform varchar(254), ninfom varchar(80), ntxtds varchar(80), picrep varchar(80), scamin numeric(24,15), txtdsc varchar(80), sordat varchar(80), sorind varchar(80)
3_coastal_siltnk_polygon (writer POSTGIS_1)
    attributes: fidn varchar(20), buishp varchar(80), catsil varchar(80), colour varchar(80), colpat varchar(80), condtn varchar(80), conrad varchar(80), convis varchar(80), elevat numeric(20,10), height numeric(20,10), natcon varchar(80), nobjnm varchar(80), objnam varchar(80), prodct varchar(80), status varchar(80), veracc numeric(20,10), verdat varchar(80), verlen numeric(20,10), inform varchar(254), ninfom varchar(80), ntxtds varchar(80), picrep varchar(80), scamin numeric(20,10), txtdsc varchar(80), sordat varchar(80), sorind varchar(80)

FME custom transformer AttributeCombiner
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with both Python 2.7 and Python 3.x interpreters.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.

Parameters:
- ATTRLIST =   # GROUP_BY " " Group By
- CHOICE = No   # ORDERED_BY_GROUP Yes%No Input is Ordered by Group
- ATTRLIST =   # ATTRS " " Attributes to Combine
- RANGE_SLIDER =   # MAX_NUM "RANGE:(0,]%PRECISION:0" Maximum Number of Features to Combine
- CHOICE = No   # DROP_EMPTY Yes%No Drop Empty String
- TEXT_EDIT = ,   # DELIM " " Delimiter String
- LOOKUP_CHOICE = None
- TEXT_EDIT =   # PREFIX " " Prefix for Each Value
- TEXT_EDIT =   # SUFFIX " " Suffix for Each Value

Input (input)
    -> ParameterFetcher
ParameterFetcher
    ATTR_LIST = __tmp.group_by $(GROUP_BY) __tmp.attrs $(ATTRS) __tmp.max_num $(MAX_NUM) __tmp.delim $(DELIM) __tmp.drop_empty $(DROP_EMPTY) __tmp.quot $(QUOT) __tmp.prefix $(PREFIX) __tmp.suffix $(SUFFIX)
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    BOOL_OP = OR
    TEST_CLAUSE:
      TEST @Value(__tmp.group_by) = ""
      TEST $(ORDERED_BY_GROUP) = Yes
    TEST_MODE = Automatic
    PASSED -> PythonCaller
    FAILED -> Sorter
Sorter
    SORT_PARM = __tmp.group ALPHA ASCENDING
    SORTED -> PythonCaller
PythonCaller
    PYTHONSOURCE:
      # 2016-04-13, Takashi Iijima, Original Implementation
      # 2018-05-07, Takashi Iijima, Suuports Python 3.x
      # 2020-01-13, Takashi Iijima, Changed Default Python Interpreter to 3.6+, saved with FME 2017.1.2.1

      import fme
      import fmeobjects, locale

      class AttributeCombiner(object):
          def __init__(self):
              import platform
              vt = platform.python_version_tuple()
              if vt[0] == '2':
                  loc = locale.getdefaultlocale()
                  enc = loc[1] if loc else 'utf_8'
                  self.toStr = lambda s: s.encode(enc) if isinstance(s, unicode) else str(s)
              else:
                  self.toStr = lambda s: s
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.items():
                          self.feature.setAttribute(attr, delim.join([fmt % v for v in values if v != '']))
                  else:
                      for attr, values in self.data.items():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    PYTHONSYMBOL = AttributeCombiner
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)
