FME workspace 2 General.fmw

Parameters:
- DestDataset_POSTGIS = Dev   # Connection
- SourceDataset_S57 = G:\LDS_vector_20210919\2 General\*.000   # Source S-57 (ENC) Hydrographic Data File(s)

Readers:
- S57_1: S57 from $(SourceDataset_S57)

Writers:
- POSTGIS_1: POSTGIS to $(DestDataset_POSTGIS)

BCNSPP (reader S57_1)
    attributes: RCID integer, PRIM integer16, GRUP integer16, OBJL integer, RVER integer16, AGEN integer, FIDN integer, FIDS integer, LNAM char(16), LNAM_REFS{} char(16), FFPT_RIND{} integer16, BCNSHP integer, CATSPM char(254), COLOUR char(254), COLPAT char(254), CONDTN integer, CONRAD integer, CONVIS integer, DATEND char(254), DATSTA char(254), ELEVAT double, HEIGHT double, MARSYS integer, NATCON char(254), NOBJNM char(254), OBJNAM char(254), PEREND char(254), PERSTA char(254), STATUS char(254), VERACC double,
      VERDAT integer, VERLEN double, INFORM char(254), NINFOM char(254), NTXTDS char(254), PICREP char(254), SCAMAX integer, SCAMIN integer, TXTDSC char(254), RECDAT char(254), RECIND char(254), SORDAT char(254), SORIND char(254)
    -> AttributeManager_26
AttributeManager_26
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_bcnspp_point (writer POSTGIS_1)
2_general_bcnspp_point (writer POSTGIS_1)
    attributes: fidn varchar(20), bcnshp varchar(80), catspm varchar(80), colour varchar(80), colpat varchar(80), condtn varchar(80), conrad varchar(80), convis varchar(80), datend varchar(80), datsta varchar(80), elevat numeric(24,15), height numeric(24,15), marsys varchar(80), natcon varchar(80), nobjnm varchar(80), objnam varchar(80), perend varchar(80), persta varchar(80), status varchar(80), veracc numeric(24,15), verdat varchar(80), verlen numeric(24,15), inform varchar(80), ninfom varchar(80), ntxtds varchar(80), picrep varchar(80), scamin numeric(24,15), txtdsc varchar(80), sordat varchar(80), sorind varchar(80)
BOYINB (reader S57_1)
    attributes: RCID integer, PRIM integer16, GRUP integer16, OBJL integer, RVER integer16, AGEN integer, FIDN integer, FIDS integer, LNAM char(16), LNAM_REFS{} char(16), FFPT_RIND{} integer16, BOYSHP integer, CATINB integer, COLOUR char(254), COLPAT char(254), CONRAD integer, DATEND char(254), DATSTA char(254), MARSYS integer, NATCON char(254), NOBJNM char(254), OBJNAM char(254), PEREND char(254), PERSTA char(254), PRODCT char(254), STATUS char(254), VERACC double, VERLEN double, INFORM char(254), NINFOM char(254),
      NTXTDS char(254), PICREP char(254), SCAMAX integer, SCAMIN integer, TXTDSC char(254), RECDAT char(254), RECIND char(254), SORDAT char(254), SORIND char(254)
    -> AttributeManager_27
AttributeManager_27
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_boyinb_point (writer POSTGIS_1)
2_general_boyinb_point (writer POSTGIS_1)
    attributes: fidn varchar(20), boyshp varchar(80), catinb varchar(80), colour varchar(80), colpat varchar(80), conrad varchar(80), datend varchar(80), datsta varchar(80), marsys varchar(80), natcon varchar(80), nobjnm varchar(80), objnam varchar(80), perend varchar(80), persta varchar(80), prodct varchar(80), status varchar(80), veracc numeric(24,15), verlen numeric(24,15), inform varchar(80), ninfom varchar(80), ntxtds varchar(80), picrep varchar(80), scamin numeric(24,15), txtdsc varchar(80), sordat varchar(80), sorind varchar(80)
BOYSPP (reader S57_1)
    attributes: RCID integer, PRIM integer16, GRUP integer16, OBJL integer, RVER integer16, AGEN integer, FIDN integer, FIDS integer, LNAM char(16), LNAM_REFS{} char(16), FFPT_RIND{} integer16, BOYSHP integer, CATSPM char(254), COLOUR char(254), COLPAT char(254), CONRAD integer, DATEND char(254), DATSTA char(254), MARSYS integer, NATCON char(254), NOBJNM char(254), OBJNAM char(254), PEREND char(254), PERSTA char(254), STATUS char(254), VERACC double, VERLEN double, INFORM char(254), NINFOM char(254), NTXTDS char(254),
      PICREP char(254), SCAMAX integer, SCAMIN integer, TXTDSC char(254), RECDAT char(254), RECIND char(254), SORDAT char(254), SORIND char(254)
    -> AttributeManager_28
AttributeManager_28
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_boyspp_point (writer POSTGIS_1)
2_general_boyspp_point (writer POSTGIS_1)
    attributes: fidn varchar(20), boyshp varchar(80), catspm varchar(80), colour varchar(80), colpat varchar(80), conrad varchar(80), datend varchar(80), datsta varchar(80), marsys varchar(80), natcon varchar(80), nobjnm varchar(80), objnam varchar(80), perend varchar(80), persta varchar(80), status varchar(80), veracc numeric(24,15), verlen numeric(24,15), inform varchar(80), ninfom varchar(80), ntxtds varchar(80), picrep varchar(80), scamin numeric(24,15), txtdsc varchar(80), sordat varchar(80), sorind varchar(80)
BUAARE (reader S57_1)
    attributes: RCID integer, PRIM integer16, GRUP integer16, OBJL integer, RVER integer16, AGEN integer, FIDN integer, FIDS integer, LNAM char(16), LNAM_REFS{} char(16), FFPT_RIND{} integer16, CATBUA integer, CONDTN integer, CONRAD integer, CONVIS integer, HEIGHT double, NOBJNM char(254), OBJNAM char(254), VERACC double, VERDAT integer, INFORM char(254), NINFOM char(254), NTXTDS char(254), PICREP char(254), SCAMAX integer, SCAMIN integer, TXTDSC char(254), RECDAT char(254), RECIND char(254), SORDAT char(254),
      SORIND char(254)
    -> AttributeManager
AttributeManager
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE PICREP
      REMOVE SCAMAX
      REMOVE RECDAT
      REMOVE RECIND
    -> GeometryFilter_2
GeometryFilter_2
    BREAK_AGG = No
    GEOM_PORT_NAMES = Point Area
    POINT -> 2_general_buaare_point (writer POSTGIS_1)
    AREA -> 2_general_buaare_polygon (writer POSTGIS_1)
2_general_buaare_point (writer POSTGIS_1)
    attributes: fidn varchar(20), catbua varchar(80), condtn varchar(80), conrad varchar(80), convis varchar(80), height numeric(24,15), nobjnm varchar(80), objnam varchar(80), veracc numeric(24,15), verdat varchar(80), inform varchar(80), ninfom varchar(80), ntxtds varchar(254), scamin numeric(24,15), txtdsc varchar(80), sordat varchar(80), sorind varchar(80)
2_general_buaare_polygon (writer POSTGIS_1)
    attributes: fidn varchar(20), catbua varchar(80), condtn varchar(80), conrad varchar(80), convis varchar(80), height numeric(24,15), nobjnm varchar(80), objnam varchar(80), veracc numeric(24,15), verdat varchar(80), inform varchar(80), ninfom varchar(80), ntxtds varchar(80), scamin numeric(24,15), txtdsc varchar(80), sordat varchar(80), sorind varchar(80)
DSID (reader S57_1)
    attributes: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
CBLSUB (reader S57_1)
    attributes: RCID integer, PRIM integer16, GRUP integer16, OBJL integer, RVER integer16, AGEN integer, FIDN integer, FIDS integer, LNAM char(16), LNAM_REFS{} char(16), FFPT_RIND{} integer16, BURDEP double, CATCBL integer, CONDTN integer, DATEND char(254), DATSTA char(254), NOBJNM char(254), OBJNAM char(254), STATUS char(254), VERDAT integer, INFORM char(254), NINFOM char(254), NTXTDS char(254), SCAMAX integer, SCAMIN integer, TXTDSC char(254), RECDAT char(254), RECIND char(254), SORDAT char(254), SORIND char(254)
    -> AttributeManager_2
AttributeManager_2
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      SET_TO drval1
      SET_TO drval2
      REMOVE SCAMAX
      REMOVE RECDAT
      REMOVE RECIND
    -> NullAttributeMapper_8
NullAttributeMapper_8
    ATTRCHOICE = Selected Attributes
    ATTRLIST = drval1 drval2
    NULL_TREATMENT = Missing
    SOURCE_ATTR_VAL = Empty
    -> 2_general_cblsub_arc (writer POSTGIS_1)
2_general_cblsub_arc (writer POSTGIS_1)
    attributes: fidn varchar(20), burdep numeric(24,15), catcbl varchar(80), condtn varchar(80), datend varchar(80), datsta varchar(80), drval1 numeric(24,15), drval2 numeric(24,15), nobjnm varchar(80), objnam varchar(80), status varchar(80), verdat varchar(80), inform varchar(80), ninfom varchar(80), ntxtds varchar(80), scamin numeric(24,15), txtdsc varchar(80), sordat varchar(80), sorind varchar(80)
COALNE (reader S57_1)
    attributes: RCID integer, PRIM integer16, GRUP integer16, OBJL integer, RVER integer16, AGEN integer, FIDN integer, FIDS integer, LNAM char(16), LNAM_REFS{} char(16), FFPT_RIND{} integer16, CATCOA integer, COLOUR char(254), CONRAD integer, CONVIS integer, ELEVAT double, NOBJNM char(254), OBJNAM char(254), VERACC double, VERDAT integer, INFORM char(254), NINFOM char(254), NTXTDS char(254), PICREP char(254), SCAMAX integer, SCAMIN integer, TXTDSC char(254), RECDAT char(254), RECIND char(254), SORDAT char(254),
      SORIND char(254)
    -> AttributeManager_3
AttributeManager_3
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_coalne_arc (writer POSTGIS_1)
2_general_coalne_arc (writer POSTGIS_1)
    attributes: fidn varchar(20), catcoa varchar(80), colour varchar(80), conrad varchar(80), convis varchar(80), elevat numeric(24,15), nobjnm varchar(80), objnam varchar(80), veracc numeric(24,15), verdat varchar(80), inform varchar(80), ninfom varchar(80), ntxtds varchar(80), picrep varchar(80), scamin numeric(24,15), txtdsc varchar(80), sordat varchar(80), sorind varchar(80)
CTNARE (reader S57_1)
    attributes: RCID integer, PRIM integer16, GRUP integer16, OBJL integer, RVER integer16, AGEN integer, FIDN integer, FIDS integer, LNAM char(16), LNAM_REFS{} char(16), FFPT_RIND{} integer16, DATEND char(254), DATSTA char(254), PEREND char(254), PERSTA char(254), INFORM char(254), NINFOM char(254), NTXTDS char(254), SCAMAX integer, SCAMIN integer, TXTDSC char(254), RECDAT char(254), RECIND char(254), SORDAT char(254), SORIND char(254)
    -> AttributeManager_29
AttributeManager_29
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_8
GeometryFilter_8
    BREAK_AGG = No
    GEOM_PORT_NAMES = Point Area
    POINT -> 2_general_ctnare_point (writer POSTGIS_1)
    AREA -> 2_general_ctnare_polygon (writer POSTGIS_1)
2_general_ctnare_point (writer POSTGIS_1)
    attributes: fidn varchar(20), datend varchar(80), datsta varchar(80), perend varchar(80), persta varchar(80), inform varchar(80), ninfom varchar(80), ntxtds varchar(80), scamin numeric(24,15), txtdsc varchar(80), sordat varchar(80), sorind varchar(80)
2_general_ctnare_polygon (writer POSTGIS_1)
    attributes: fidn varchar(20), datend varchar(80), datsta varchar(80), perend varchar(80), persta varchar(80), inform varchar(80), ninfom varchar(80), ntxtds varchar(80), scamin numeric(24,15), txtdsc varchar(80), sordat varchar(80), sorind varchar(80)
CURENT (reader S57_1)
    attributes: RCID integer, PRIM integer16, GRUP integer16, OBJL integer, RVER integer16, AGEN integer, FIDN integer, FIDS integer, LNAM char(16), LNAM_REFS{} char(16), FFPT_RIND{} integer16, CURVEL double, DATEND char(254), DATSTA char(254), NOBJNM char(254), OBJNAM char(254), ORIENT double, PEREND char(254), PERSTA char(254), INFORM char(254), NINFOM char(254), SCAMAX integer, SCAMIN integer, RECDAT char(254), RECIND char(254), SORDAT char(254), SORIND char(254)
    -> AttributeManager_4
AttributeManager_4
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> NullAttributeMapper_7
NullAttributeMapper_7
    ATTRCHOICE = Selected Attributes
    ATTRLIST = CURVEL
    NULL_TREATMENT = Missing
    SOURCE_ATTR_VAL = Empty
    -> 2_general_curent_point (writer POSTGIS_1)
2_general_curent_point (writer POSTGIS_1)
    attributes: fidn varchar(20), curvel numeric(24,15), datend varchar(80), datsta varchar(80), nobjnm varchar(80), objnam varchar(80), orient numeric(24,15), perend varchar(80), persta varchar(80), inform varchar(80), ninfom varchar(80), scamin numeric(24,15), sordat varchar(80), sorind varchar(80)
DEPARE (reader S57_1)
    attributes: RCID integer, PRIM integer16, GRUP integer16, OBJL integer, RVER integer16, AGEN integer, FIDN integer, FIDS integer, LNAM char(16), LNAM_REFS{} char(16), FFPT_RIND{} integer16, DRVAL1 double, DRVAL2 double, QUASOU char(254), SOUACC double, VERDAT integer, INFORM char(254), NINFOM char(254), NTXTDS char(254), SCAMAX integer, SCAMIN integer, TXTDSC char(254), RECDAT char(254), RECIND char(254), SORDAT char(254), SORIND char(254)
    -> AttributeManager_6
AttributeManager_6
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> NullAttributeMapper
NullAttributeMapper
    ATTRCHOICE = Selected Attributes
    ATTRLIST = DRVAL1
    NULL_TREATMENT = Missing
    SOURCE_ATTR_VAL = Empty
    -> 2_general_depare_polygon (writer POSTGIS_1)
2_general_depare_polygon (writer POSTGIS_1)
    attributes: fidn varchar(20), drval1 numeric(24,15), drval2 numeric(24,15), quasou varchar(80), souacc numeric(24,15), verdat varchar(80), inform varchar(80), ninfom varchar(80), ntxtds varchar(80), scamin numeric(24,15), txtdsc varchar(80), sordat varchar(80), sorind varchar(80)
DEPCNT (reader S57_1)
    attributes: RCID integer, PRIM integer16, GRUP integer16, OBJL integer, RVER integer16, AGEN integer, FIDN integer, FIDS integer, LNAM char(16), LNAM_REFS{} char(16), FFPT_RIND{} integer16, VALDCO double, VERDAT integer, INFORM char(254), NINFOM char(254), NTXTDS char(254), SCAMAX integer, SCAMIN integer, TXTDSC char(254), RECDAT char(254), RECIND char(254), SORDAT char(254), SORIND char(254)
    -> AttributeManager_7
AttributeManager_7
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      SET_TO HYPCAT
    -> NullAttributeMapper_9
NullAttributeMapper_9
    ATTRCHOICE = Selected Attributes
    ATTRLIST = HYPCAT
    NULL_TREATMENT = Missing
    SOURCE_ATTR_VAL = Empty
    -> 2_general_depcnt_arc (writer POSTGIS_1)
2_general_depcnt_arc (writer POSTGIS_1)
    attributes: fidn varchar(20), valdco numeric(24,15), verdat varchar(80), inform varchar(80), ninfom varchar(80), ntxtds varchar(80), scamin numeric(24,15), txtdsc varchar(80), sordat varchar(80), sorind varchar(80), hypcat numeric(24,15)
EXEZNE (reader S57_1)
    attributes: RCID integer, PRIM integer16, GRUP integer16, OBJL integer, RVER integer16, AGEN integer, FIDN integer, FIDS integer, LNAM char(16), LNAM_REFS{} char(16), FFPT_RIND{} integer16, NATION char(254), INFORM char(254), NINFOM char(254), NTXTDS char(254), SCAMAX integer, SCAMIN integer, TXTDSC char(254), RECDAT char(254), RECIND char(254), SORDAT char(254), SORIND char(254)
    -> AttributeManager_8
AttributeManager_8
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_exezne_polygon (writer POSTGIS_1)
2_general_exezne_polygon (writer POSTGIS_1)
    attributes: fidn varchar(20), nation varchar(80), inform varchar(80), ninfom varchar(80), ntxtds varchar(80), scamin numeric(24,15), txtdsc varchar(80), sordat varchar(80), sorind varchar(80)
FOGSIG (reader S57_1)
    attributes: RCID integer, PRIM integer16, GRUP integer16, OBJL integer, RVER integer16, AGEN integer, FIDN integer, FIDS integer, LNAM char(16), LNAM_REFS{} char(16), FFPT_RIND{} integer16, CATFOG integer, DATEND char(254), DATSTA char(254), NOBJNM char(254), OBJNAM char(254), SIGFRQ integer, SIGGEN integer, SIGGRP char(254), SIGPER double, SIGSEQ char(254), STATUS char(254), VALMXR double, INFORM char(254), NINFOM char(254), NTXTDS char(254), SCAMAX integer, SCAMIN integer, TXTDSC char(254), RECDAT char(254),
      RECIND char(254), SORDAT char(254), SORIND char(254)
    -> AttributeManager_5
AttributeManager_5
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_fogsig_point (writer POSTGIS_1)
2_general_fogsig_point (writer POSTGIS_1)
    attributes: fidn varchar(20), catfog varchar(80), datend varchar(80), datsta varchar(80), nobjnm varchar(80), objnam varchar(80), sigfrq numeric(24,15), siggen varchar(80), siggrp varchar(80), sigper numeric(24,15), sigseq varchar(80), status varchar(80), valmxr numeric(24,15), inform varchar(80), ninfom varchar(80), ntxtds varchar(80), scamin numeric(24,15), txtdsc varchar(80), sordat varchar(80), sorind varchar(80)
Generic (reader S57_1)
    attributes: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
LAKARE (reader S57_1)
    attributes: RCID integer, PRIM integer16, GRUP integer16, OBJL integer, RVER integer16, AGEN integer, FIDN integer, FIDS integer, LNAM char(16), LNAM_REFS{} char(16), FFPT_RIND{} integer16, ELEVAT double, NOBJNM char(254), OBJNAM char(254), VERACC double, VERDAT integer, INFORM char(254), NINFOM char(254), NTXTDS char(254), SCAMAX integer, SCAMIN integer, TXTDSC char(254), RECDAT char(254), RECIND char(254), SORDAT char(254), SORIND char(254)
    -> AttributeManager_30
AttributeManager_30
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_lakare_polygon (writer POSTGIS_1)
2_general_lakare_polygon (writer POSTGIS_1)
    attributes: fidn varchar(20), elevat numeric(24,15), nobjnm varchar(80), objnam varchar(80), veracc numeric(24,15), verdat varchar(80), inform varchar(80), ninfom varchar(80), ntxtds varchar(80), scamin numeric(24,15), txtdsc varchar(80), sordat varchar(80), sorind varchar(80)
LIGHTS (reader S57_1)
    attributes: RCID integer, PRIM integer16, GRUP integer16, OBJL integer, RVER integer16, AGEN integer, FIDN integer, FIDS integer, LNAM char(16), LNAM_REFS{} char(16), FFPT_RIND{} integer16, CATLIT char(254), COLOUR char(254), DATEND char(254), DATSTA char(254), EXCLIT integer, HEIGHT double, LITCHR integer, LITVIS char(254), MARSYS integer, MLTYLT integer, NOBJNM char(254), OBJNAM char(254), ORIENT double, PEREND char(254), PERSTA char(254), SECTR1 double, SECTR2 double, SIGGRP char(254), SIGPER double,
      SIGSEQ char(254), STATUS char(254), VERACC double, VALNMR double, VERDAT integer, INFORM char(254), NINFOM char(254), NTXTDS char(254), SCAMAX integer, SCAMIN integer, TXTDSC char(254), RECDAT char(254), RECIND char(254), SORDAT char(254), SORIND char(254)
    -> AttributeManager_9
AttributeManager_9
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> NullAttributeMapper_2
NullAttributeMapper_2
    ATTRCHOICE = Selected Attributes
    ATTRLIST = SIGPER
    NULL_TREATMENT = Missing
    SOURCE_ATTR_VAL = Empty
    -> 2_general_lights_point (writer POSTGIS_1)
2_general_lights_point (writer POSTGIS_1)
    attributes: fidn varchar(20), catlit varchar(80), colour varchar(80), datend varchar(80), datsta varchar(80), exclit varchar(80), height numeric(24,15), litchr varchar(80), litvis varchar(254), marsys varchar(80), mltylt numeric(24,15), nobjnm varchar(80), objnam varchar(80), orient numeric(24,15), perend varchar(80), persta varchar(80), sectr1 numeric(24,15), sectr2 numeric(24,15), siggrp varchar(80), sigper numeric(24,15), sigseq varchar(80), status varchar(80), veracc numeric(24,15), valnmr numeric(24,15), verdat varchar(80), inform varchar(130), ninfom varchar(80), ntxtds varchar(80), scamin numeric(24,15), txtdsc varchar(80),
      sordat varchar(80), sorind varchar(80)
LNDARE (reader S57_1)
    attributes: RCID integer, PRIM integer16, GRUP integer16, OBJL integer, RVER integer16, AGEN integer, FIDN integer, FIDS integer, LNAM char(16), LNAM_REFS{} char(16), FFPT_RIND{} integer16, CONDTN integer, NOBJNM char(254), OBJNAM char(254), STATUS char(254), INFORM char(254), NINFOM char(254), NTXTDS char(254), SCAMAX integer, SCAMIN integer, TXTDSC char(254), RECDAT char(254), RECIND char(254), SORDAT char(254), SORIND char(254)
    -> AttributeManager_10
AttributeManager_10
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter
GeometryFilter
    BREAK_AGG = No
    GEOM_PORT_NAMES = Point Area
    POINT -> 2_general_lndare_point (writer POSTGIS_1)
    AREA -> 2_general_lndare_polygon (writer POSTGIS_1)
2_general_lndare_point (writer POSTGIS_1)
    attributes: fidn varchar(20), condtn varchar(80), nobjnm varchar(80), objnam varchar(80), status varchar(80), inform varchar(80), ninfom varchar(80), ntxtds varchar(80), scamin numeric(24,15), txtdsc varchar(80), sordat varchar(80), sorind varchar(80)
2_general_lndare_polygon (writer POSTGIS_1)
    attributes: fidn varchar(20), condtn varchar(80), nobjnm varchar(80), objnam varchar(80), status varchar(80), inform varchar(80), ninfom varchar(80), ntxtds varchar(80), scamin numeric(24,15), txtdsc varchar(80), sordat varchar(80), sorind varchar(80)
LNDELV (reader S57_1)
    attributes: RCID integer, PRIM integer16, GRUP integer16, OBJL integer, RVER integer16, AGEN integer, FIDN integer, FIDS integer, LNAM char(16), LNAM_REFS{} char(16), FFPT_RIND{} integer16, CONVIS integer, ELEVAT double, NOBJNM char(254), OBJNAM char(254), VERACC double, VERDAT integer, INFORM char(254), NINFOM char(254), NTXTDS char(254), SCAMAX integer, SCAMIN integer, TXTDSC char(254), RECDAT char(254), RECIND char(254), SORDAT char(254), SORIND char(254)
    -> AttributeManager_12
AttributeManager_12
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_lndelv_point (writer POSTGIS_1)
2_general_lndelv_point (writer POSTGIS_1)
    attributes: fidn varchar(20), convis varchar(80), elevat numeric(24,15), nobjnm varchar(80), objnam varchar(80), veracc numeric(24,15), verdat varchar(80), inform varchar(80), ninfom varchar(80), ntxtds varchar(80), scamin numeric(24,15), txtdsc varchar(80), sordat varchar(80), sorind varchar(80)
LNDMRK (reader S57_1)
    attributes: RCID integer, PRIM integer16, GRUP integer16, OBJL integer, RVER integer16, AGEN integer, FIDN integer, FIDS integer, LNAM char(16), LNAM_REFS{} char(16), FFPT_RIND{} integer16, CATLMK char(254), COLOUR char(254), COLPAT char(254), CONDTN integer, CONRAD integer, CONVIS integer, ELEVAT double, FUNCTN char(254), HEIGHT double, NATCON char(254), NOBJNM char(254), OBJNAM char(254), STATUS char(254), VERACC double, VERDAT integer, VERLEN double, INFORM char(254), NINFOM char(254), NTXTDS char(254),
      PICREP char(254), SCAMAX integer, SCAMIN integer, TXTDSC char(254), RECDAT char(254), RECIND char(254), SORDAT char(254), SORIND char(254)
    -> AttributeManager_13
AttributeManager_13
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE PICREP
      REMOVE SCAMAX
      REMOVE RECDAT
      REMOVE RECIND
    -> 2_general_lndmrk_point (writer POSTGIS_1)
2_general_lndmrk_point (writer POSTGIS_1)
    attributes: fidn varchar(20), catlmk varchar(80), colour varchar(80), colpat varchar(80), condtn varchar(80), conrad varchar(80), convis varchar(80), elevat numeric(24,15), functn varchar(80), height numeric(24,15), natcon varchar(80), nobjnm varchar(80), objnam varchar(80), status varchar(80), veracc numeric(24,15), verdat varchar(80), verlen numeric(24,15), inform varchar(100), ninfom varchar(80), ntxtds varchar(80), scamin numeric(24,15), txtdsc varchar(80), sordat varchar(80), sorind varchar(80)
LNDRGN (reader S57_1)
    attributes: RCID integer, PRIM integer16, GRUP integer16, OBJL integer, RVER integer16, AGEN integer, FIDN integer, FIDS integer, LNAM char(16), LNAM_REFS{} char(16), FFPT_RIND{} integer16, CATLND char(254), NATQUA char(254), NATSUR char(254), NOBJNM char(254), OBJNAM char(254), WATLEV integer, INFORM char(254), NINFOM char(254), NTXTDS char(254), SCAMAX integer, SCAMIN integer, TXTDSC char(254), RECDAT char(254), RECIND char(254), SORDAT char(254), SORIND char(254)
    -> AttributeManager_14
AttributeManager_14
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_3
GeometryFilter_3
    BREAK_AGG = No
    GEOM_PORT_NAMES = Point Area
    POINT -> 2_general_lndrgn_point (writer POSTGIS_1)
    AREA -> 2_general_lndrgn_polygon (writer POSTGIS_1)
2_general_lndrgn_point (writer POSTGIS_1)
    attributes: fidn varchar(20), catlnd varchar(80), natqua varchar(80), natsur varchar(80), nobjnm varchar(80), objnam varchar(80), watlev varchar(80), inform varchar(80), ninfom varchar(80), ntxtds varchar(80), scamin numeric(24,15), txtdsc varchar(80), sordat varchar(80), sorind varchar(80)
2_general_lndrgn_polygon (writer POSTGIS_1)
    attributes: fidn varchar(20), catlnd varchar(80), natqua varchar(80), natsur varchar(80), nobjnm varchar(80), objnam varchar(80), watlev varchar(80), inform varchar(80), ninfom varchar(80), ntxtds varchar(80), scamin numeric(24,15), txtdsc varchar(80), sordat varchar(80), sorind varchar(80)
LOCMAG (reader S57_1)
    attributes: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
M_COVR (reader S57_1)
    attributes: RCID integer, PRIM integer16, GRUP integer16, OBJL integer, RVER integer16, AGEN integer, FIDN integer, FIDS integer, LNAM char(16), LNAM_REFS{} char(16), FFPT_RIND{} integer16, CATCOV integer, INFORM char(254), NINFOM char(254), RECDAT char(254), RECIND char(254), SORDAT char(254), SORIND char(254)
    -> AttributeManager_15
AttributeManager_15
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
    -> 2_general_m_covr_polygon (writer POSTGIS_1)
2_general_m_covr_polygon (writer POSTGIS_1)
    attributes: fidn varchar(20), catcov varchar(80), inform varchar(80), ninfom varchar(80), sordat varchar(80), sorind varchar(80)
M_NPUB (reader S57_1)
    attributes: RCID integer, PRIM integer16, GRUP integer16, OBJL integer, RVER integer16, AGEN integer, FIDN integer, FIDS integer, LNAM char(16), LNAM_REFS{} char(16), FFPT_RIND{} integer16, INFORM char(254), NINFOM char(254), NTXTDS char(254), PICREP char(254), PUBREF char(254), TXTDSC char(254), RECDAT char(254), RECIND char(254), SORDAT char(254), SORIND char(254)
    -> AttributeManager_16
AttributeManager_16
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
    -> 2_general_m_npub_polygon (writer POSTGIS_1)
2_general_m_npub_polygon (writer POSTGIS_1)
    attributes: fidn varchar(20), inform varchar(80), ninfom varchar(80), ntxtds varchar(80), picrep varchar(80), pubref varchar(80), txtdsc varchar(80), sordat varchar(80), sorind varchar(80)
M_NSYS (reader S57_1)
    attributes: RCID integer, PRIM integer16, GRUP integer16, OBJL integer, RVER integer16, AGEN integer, FIDN integer, FIDS integer, LNAM char(16), LNAM_REFS{} char(16), FFPT_RIND{} integer16, MARSYS integer, ORIENT double, INFORM char(254), NINFOM char(254), NTXTDS char(254), SCAMAX integer, SCAMIN integer, TXTDSC char(254), RECDAT char(254), RECIND char(254), SORDAT char(254), SORIND char(254)
    -> AttributeManager_17
AttributeManager_17
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_m_nsys_polygon (writer POSTGIS_1)
2_general_m_nsys_polygon (writer POSTGIS_1)
    attributes: fidn varchar(20), marsys varchar(80), orient numeric(24,15), inform varchar(80), ninfom varchar(80), ntxtds varchar(80), scamin numeric(24,15), txtdsc varchar(80), sordat varchar(80), sorind varchar(80)
M_QUAL (reader S57_1)
    attributes: RCID integer, PRIM integer16, GRUP integer16, OBJL integer, RVER integer16, AGEN integer, FIDN integer, FIDS integer, LNAM char(16), LNAM_REFS{} char(16), FFPT_RIND{} integer16, CATQUA integer, CATZOC integer, DRVAL1 double, DRVAL2 double, POSACC double, SOUACC double, SUREND char(254), SURSTA char(254), TECSOU char(254), VERDAT integer, INFORM char(254), NINFOM char(254), NTXTDS char(254), TXTDSC char(254), RECDAT char(254), RECIND char(254), SORDAT char(254), SORIND char(254)
    -> AttributeManager_18
AttributeManager_18
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
    -> 2_general_m_qual_polygon (writer POSTGIS_1)
2_general_m_qual_polygon (writer POSTGIS_1)
    attributes: fidn varchar(20), catqua varchar(80), catzoc varchar(80), drval1 numeric(24,15), drval2 numeric(24,15), posacc numeric(24,15), souacc numeric(24,15), surend varchar(80), sursta varchar(80), tecsou varchar(80), verdat varchar(80), inform varchar(80), ninfom varchar(80), ntxtds varchar(80), txtdsc varchar(80), sordat varchar(80), sorind varchar(80)
MAGVAR (reader S57_1)
    attributes: RCID integer, PRIM integer16, GRUP integer16, OBJL integer, RVER integer16, AGEN integer, FIDN integer, FIDS integer, LNAM char(16), LNAM_REFS{} char(16), FFPT_RIND{} integer16, DATEND char(254), DATSTA char(254), RYRMGV char(254), VALACM double, VALMAG double, INFORM char(254), NINFOM char(254), SCAMAX integer, SCAMIN integer, RECDAT char(254), RECIND char(254), SORDAT char(254), SORIND char(254)
    -> AttributeManager_19
AttributeManager_19
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_magvar_arc (writer POSTGIS_1)
2_general_magvar_arc (writer POSTGIS_1)
    attributes: fidn varchar(20), datend varchar(80), datsta varchar(80), ryrmgv varchar(80), valacm numeric(24,15), valmag numeric(24,15), inform varchar(80), ninfom varchar(80), scamin numeric(24,15), sordat varchar(80), sorind varchar(80)
OBSTRN (reader S57_1)
    attributes: RCID integer, PRIM integer16, GRUP integer16, OBJL integer, RVER integer16, AGEN integer, FIDN integer, FIDS integer, LNAM char(16), LNAM_REFS{} char(16), FFPT_RIND{} integer16, CATOBS integer, CONDTN integer, EXPSOU integer, HEIGHT double, NATCON char(254), NATQUA char(254), NOBJNM char(254), OBJNAM char(254), PRODCT char(254), QUASOU char(254), SOUACC double, STATUS char(254), TECSOU char(254), VALSOU double, VERACC double, VERDAT integer, VERLEN double, WATLEV integer, NATSUR char(254),
      INFORM char(254), NINFOM char(254), NTXTDS char(254), SCAMAX integer, SCAMIN integer, TXTDSC char(254), RECDAT char(254), RECIND char(254), SORDAT char(254), SORIND char(254)
    -> AttributeManager_20
AttributeManager_20
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_4
GeometryFilter_4
    BREAK_AGG = No
    GEOM_PORT_NAMES = Point Area
    POINT -> NullAttributeMapper_5
    AREA -> NullAttributeMapper_4
NullAttributeMapper_5
    ATTRCHOICE = Selected Attributes
    ATTRLIST = VALSOU
    NULL_TREATMENT = Missing
    SOURCE_ATTR_VAL = Empty
    -> 2_general_obstrn_point (writer POSTGIS_1)
2_general_obstrn_point (writer POSTGIS_1)
    attributes: fidn varchar(20), catobs varchar(80), condtn varchar(80), expsou varchar(80), height numeric(24,15), natcon varchar(80), natqua varchar(80), nobjnm varchar(80), objnam varchar(80), prodct varchar(80), quasou varchar(80), souacc numeric(24,15), status varchar(80), tecsou varchar(80), valsou numeric(24,15), veracc numeric(24,15), verdat varchar(80), verlen numeric(24,15), watlev varchar(80), natsur varchar(80), inform varchar(80), ninfom varchar(80), ntxtds varchar(80), scamin numeric(24,15), txtdsc varchar(80), sordat varchar(80), sorind varchar(80)
NullAttributeMapper_4
    ATTRCHOICE = Selected Attributes
    ATTRLIST = VALSOU
    NULL_TREATMENT = Missing
    SOURCE_ATTR_VAL = Empty
    -> 2_general_obstrn_polygon (writer POSTGIS_1)
2_general_obstrn_polygon (writer POSTGIS_1)
    attributes: fidn varchar(20), catobs varchar(80), condtn varchar(80), expsou varchar(80), height numeric(24,15), natcon varchar(80), natqua varchar(80), nobjnm varchar(80), objnam varchar(80), prodct varchar(80), quasou varchar(80), souacc numeric(24,15), status varchar(80), tecsou varchar(80), valsou numeric(20,15), veracc numeric(20,15), verdat varchar(80), verlen numeric(24,15), watlev varchar(80), natsur varchar(80), inform varchar(80), ninfom varchar(80), ntxtds varchar(80), scamin numeric(24,15), txtdsc varchar(80), sordat varchar(80), sorind varchar(80)
OFSPLF (reader S57_1)
    attributes: RCID integer, PRIM integer16, GRUP integer16, OBJL integer, RVER integer16, AGEN integer, FIDN integer, FIDS integer, LNAM char(16), LNAM_REFS{} char(16), FFPT_RIND{} integer16, CATOFP char(254), COLOUR char(254), COLPAT char(254), CONDTN integer, CONRAD integer, CONVIS integer, DATEND char(254), DATSTA char(254), HEIGHT double, NATCON char(254), NOBJNM char(254), OBJNAM char(254), PRODCT char(254), STATUS char(254), VERACC double, VERDAT integer, VERLEN double, INFORM char(254), NINFOM char(254),
      NTXTDS char(254), PICREP char(254), SCAMAX integer, SCAMIN integer, TXTDSC char(254), RECDAT char(254), RECIND char(254), SORDAT char(254), SORIND char(254)
    -> AttributeManager_31
AttributeManager_31
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_ofsplf_point (writer POSTGIS_1)
2_general_ofsplf_point (writer POSTGIS_1)
    attributes: fidn varchar(20), catofp varchar(80), colour varchar(80), colpat varchar(80), condtn varchar(80), conrad varchar(80), convis varchar(80), datend varchar(80), datsta varchar(80), height numeric(24,15), natcon varchar(80), nobjnm varchar(80), objnam varchar(80), prodct varchar(80), status varchar(80), veracc numeric(24,15), verdat varchar(80), verlen numeric(24,15), inform varchar(80), ninfom varchar(80), ntxtds varchar(80), picrep varchar(80), scamin numeric(24,15), txtdsc varchar(80), sordat varchar(80), sorind varchar(80)
PIPSOL (reader S57_1)
    attributes: RCID integer, PRIM integer16, GRUP integer16, OBJL integer, RVER integer16, AGEN integer, FIDN integer, FIDS integer, LNAM char(16), LNAM_REFS{} char(16), FFPT_RIND{} integer16, BURDEP double, CATPIP char(254), CONDTN integer, DATEND char(254), DATSTA char(254), DRVAL1 double, DRVAL2 double, NOBJNM char(254), OBJNAM char(254), PRODCT char(254), STATUS char(254), VERACC double, VERLEN double, VERDAT integer, INFORM char(254), NINFOM char(254), NTXTDS char(254), SCAMAX integer, SCAMIN integer,
      TXTDSC char(254), RECDAT char(254), RECIND char(254), SORDAT char(254), SORIND char(254)
    -> AttributeManager_32
AttributeManager_32
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_pipsol_arc (writer POSTGIS_1)
2_general_pipsol_arc (writer POSTGIS_1)
    attributes: fidn varchar(20), burdep numeric(24,15), catpip varchar(80), condtn varchar(80), datend varchar(80), datsta varchar(80), drval1 numeric(24,15), drval2 numeric(24,15), nobjnm varchar(80), objnam varchar(80), prodct varchar(80), status varchar(80), veracc numeric(24,15), verlen numeric(24,15), verdat varchar(80), inform varchar(80), ninfom varchar(80), ntxtds varchar(80), scamin numeric(24,15), txtdsc varchar(80), sordat varchar(80), sorind varchar(80)
PRCARE (reader S57_1)
    attributes: RCID integer, PRIM integer16, GRUP integer16, OBJL integer, RVER integer16, AGEN integer, FIDN integer, FIDS integer, LNAM char(16), LNAM_REFS{} char(16), FFPT_RIND{} integer16, DATEND char(254), DATSTA char(254), RESTRN char(254), STATUS char(254), INFORM char(254), NINFOM char(254), NTXTDS char(254), SCAMAX integer, SCAMIN integer, TXTDSC char(254), RECDAT char(254), RECIND char(254), SORDAT char(254), SORIND char(254)
    -> AttributeManager_33
AttributeManager_33
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_prcare_polygon (writer POSTGIS_1)
2_general_prcare_polygon (writer POSTGIS_1)
    attributes: fidn varchar(20), datend varchar(80), datsta varchar(80), restrn varchar(80), status varchar(80), inform varchar(254), ninfom varchar(80), ntxtds varchar(80), scamin numeric(24,15), txtdsc varchar(80), sordat varchar(80), sorind varchar(80)
RDOSTA (reader S57_1)
    attributes: RCID integer, PRIM integer16, GRUP integer16, OBJL integer, RVER integer16, AGEN integer, FIDN integer, FIDS integer, LNAM char(16), LNAM_REFS{} char(16), FFPT_RIND{} integer16, CALSGN char(254), CATROS char(254), COMCHA char(254), DATEND char(254), DATSTA char(254), ESTRNG double, NOBJNM char(254), OBJNAM char(254), ORIENT double, PEREND char(254), PERSTA char(254), SIGFRQ integer, STATUS char(254), INFORM char(254), NINFOM char(254), NTXTDS char(254), SCAMAX integer, SCAMIN integer, TXTDSC char(254),
      RECDAT char(254), RECIND char(254), SORDAT char(254), SORIND char(254)
    -> AttributeManager_22
AttributeManager_22
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_rdosta_point (writer POSTGIS_1)
2_general_rdosta_point (writer POSTGIS_1)
    attributes: fidn varchar(20), calsgn varchar(80), catros varchar(80), comcha varchar(80), datend varchar(80), datsta varchar(80), estrng numeric(24,15), nobjnm varchar(80), objnam varchar(80), orient numeric(24,15), perend varchar(80), persta varchar(80), sigfrq numeric(24,15), status varchar(80), inform varchar(80), ninfom varchar(80), ntxtds varchar(80), scamin numeric(24,15), txtdsc varchar(80), sordat varchar(80), sorind varchar(80)
RESARE (reader S57_1)
    attributes: RCID integer, PRIM integer16, GRUP integer16, OBJL integer, RVER integer16, AGEN integer, FIDN integer, FIDS integer, LNAM char(16), LNAM_REFS{} char(16), FFPT_RIND{} integer16, CATREA char(254), DATEND char(254), DATSTA char(254), NOBJNM char(254), OBJNAM char(254), PEREND char(254), PERSTA char(254), RESTRN char(254), STATUS char(254), INFORM char(254), NINFOM char(254), NTXTDS char(254), SCAMAX integer, SCAMIN integer, TXTDSC char(254), RECDAT char(254), RECIND char(254), SORDAT char(254), SORIND char(254)
    -> AttributeManager_34
AttributeManager_34
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_resare_polygon (writer POSTGIS_1)
2_general_resare_polygon (writer POSTGIS_1)
    attributes: fidn varchar(20), catrea varchar(80), datend varchar(80), datsta varchar(80), nobjnm varchar(80), objnam varchar(80), perend varchar(80), persta varchar(80), restrn varchar(80), status varchar(80), inform varchar(254), ninfom varchar(80), ntxtds varchar(80), scamin numeric(24,15), txtdsc varchar(80), sordat varchar(80), sorind varchar(80)
RIVERS (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), STATUS char(254), INFORM char(254), NINFOM char(254), NTXTDS char(254), SCAMAX integer, SCAMIN integer, TXTDSC char(254), RECDAT char(254), RECIND char(254), SORDAT char(254), SORIND char(254)
    -> AttributeManager_35
AttributeManager_35
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_rivers_arc (writer POSTGIS_1)
2_general_rivers_arc (writer POSTGIS_1)
    attributes: fidn varchar(20), nobjnm varchar(80), objnam varchar(80), status varchar(80), inform varchar(80), ninfom varchar(80), ntxtds varchar(80), scamin numeric(24,15), txtdsc varchar(80), sordat varchar(80), sorind varchar(80)
RTPBCN (reader S57_1)
    attributes: RCID integer, PRIM integer16, GRUP integer16, OBJL integer, RVER integer16, AGEN integer, FIDN integer, FIDS integer, LNAM char(16), LNAM_REFS{} char(16), FFPT_RIND{} integer16, CATRTB integer, DATEND char(254), DATSTA char(254), NOBJNM char(254), OBJNAM char(254), RADWAL char(254), SECTR1 double, SECTR2 double, SIGGRP char(254), SIGSEQ char(254), STATUS char(254), VALMXR double, INFORM char(254), NINFOM char(254), NTXTDS char(254), SCAMAX integer, SCAMIN integer, TXTDSC char(254), RECDAT char(254),
      RECIND char(254), SORDAT char(254), SORIND char(254)
    -> AttributeManager_36
AttributeManager_36
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_rtpbcn_point (writer POSTGIS_1)
2_general_rtpbcn_point (writer POSTGIS_1)
    attributes: fidn varchar(20), catrtb varchar(80), datend varchar(80), datsta varchar(80), nobjnm varchar(80), objnam varchar(80), radwal varchar(80), sectr1 numeric(24,15), sectr2 numeric(24,15), siggrp varchar(80), sigseq varchar(80), status varchar(80), valmxr numeric(24,15), inform varchar(80), ninfom varchar(80), ntxtds varchar(80), scamin numeric(24,15), txtdsc varchar(80), sordat varchar(80), sorind varchar(80)
SBDARE (reader S57_1)
    attributes: RCID integer, PRIM integer16, GRUP integer16, OBJL integer, RVER integer16, AGEN integer, FIDN integer, FIDS integer, LNAM char(16), LNAM_REFS{} char(16), FFPT_RIND{} integer16, COLOUR char(254), NATQUA char(254), NATSUR char(254), WATLEV integer, OBJNAM char(254), NOBJNM char(254), INFORM char(254), NINFOM char(254), NTXTDS char(254), SCAMAX integer, SCAMIN integer, TXTDSC char(254), RECDAT char(254), RECIND char(254), SORDAT char(254), SORIND char(254)
    -> AttributeManager_23
AttributeManager_23
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_5
GeometryFilter_5
    BREAK_AGG = No
    GEOM_PORT_NAMES = Point Area
    POINT -> 2_general_sbdare_point (writer POSTGIS_1)
    AREA -> 2_general_sbdare_polygon (writer POSTGIS_1)
2_general_sbdare_point (writer POSTGIS_1)
    attributes: fidn varchar(20), colour varchar(80), natqua varchar(80), natsur varchar(80), watlev varchar(80), objnam varchar(80), nobjnm varchar(80), inform varchar(80), ninfom varchar(80), ntxtds varchar(80), scamin numeric(24,15), txtdsc varchar(80), sordat varchar(80), sorind varchar(80)
2_general_sbdare_polygon (writer POSTGIS_1)
    attributes: fidn varchar(20), colour varchar(80), natqua varchar(80), natsur varchar(80), watlev varchar(80), objnam varchar(80), nobjnm varchar(80), inform varchar(80), ninfom varchar(80), ntxtds varchar(80), scamin numeric(24,15), txtdsc varchar(80), sordat varchar(80), sorind varchar(80)
SEAARE (reader S57_1)
    attributes: RCID integer, PRIM integer16, GRUP integer16, OBJL integer, RVER integer16, AGEN integer, FIDN integer, FIDS integer, LNAM char(16), LNAM_REFS{} char(16), FFPT_RIND{} integer16, CATSEA integer, NOBJNM char(254), OBJNAM char(254), INFORM char(254), NINFOM char(254), NTXTDS char(254), SCAMAX integer, SCAMIN integer, TXTDSC char(254), RECDAT char(254), RECIND char(254), SORDAT char(254), SORIND char(254)
    -> AttributeManager_11
AttributeManager_11
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_6
GeometryFilter_6
    BREAK_AGG = No
    GEOM_PORT_NAMES = Point Area
    POINT -> 2_general_seaare_point (writer POSTGIS_1)
    AREA -> 2_general_seaare_polygon (writer POSTGIS_1)
2_general_seaare_point (writer POSTGIS_1)
    attributes: fidn varchar(20), catsea varchar(80), nobjnm varchar(80), objnam varchar(80), inform varchar(80), ninfom varchar(80), ntxtds varchar(80), scamin numeric(24,15), txtdsc varchar(80), sordat varchar(80), sorind varchar(80)
2_general_seaare_polygon (writer POSTGIS_1)
    attributes: fidn varchar(20), catsea varchar(80), nobjnm varchar(80), objnam varchar(80), inform varchar(80), ninfom varchar(80), ntxtds varchar(80), scamin numeric(24,0), txtdsc varchar(80), sordat varchar(80), sorind varchar(80)
SLCONS (reader S57_1)
    attributes: RCID integer, PRIM integer16, GRUP integer16, OBJL integer, RVER integer16, AGEN integer, FIDN integer, FIDS integer, LNAM char(16), LNAM_REFS{} char(16), FFPT_RIND{} integer16, CATSLC integer, COLOUR char(254), COLPAT char(254), CONDTN integer, CONRAD integer, CONVIS integer, DATEND char(254), DATSTA char(254), HEIGHT double, HORACC double, HORCLR double, HORLEN double, HORWID double, NATCON char(254), NOBJNM char(254), OBJNAM char(254), STATUS char(254), VERACC double, VERDAT integer,
      VERLEN double, WATLEV integer, INFORM char(254), NINFOM char(254), NTXTDS char(254), SCAMAX integer, SCAMIN integer, TXTDSC char(254), RECDAT char(254), RECIND char(254), SORDAT char(254), SORIND char(254)
    -> AttributeManager_37
AttributeManager_37
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_slcons_arc (writer POSTGIS_1)
2_general_slcons_arc (writer POSTGIS_1)
    attributes: fidn varchar(20), catslc varchar(80), colour varchar(80), colpat varchar(80), condtn varchar(80), conrad varchar(80), convis varchar(80), datend varchar(80), datsta varchar(80), height numeric(24,15), horacc numeric(24,15), horclr numeric(24,15), horlen numeric(24,15), horwid numeric(24,15), natcon varchar(80), nobjnm varchar(80), objnam varchar(80), status varchar(80), veracc numeric(24,15), verdat varchar(80), verlen numeric(24,15), watlev varchar(80), inform varchar(80), ninfom varchar(80), ntxtds varchar(80), scamin numeric(24,15), txtdsc varchar(80), sordat varchar(80), sorind varchar(80)
SOUNDG (reader S57_1)
    attributes: RCID integer, PRIM integer16, GRUP integer16, OBJL integer, RVER integer16, AGEN integer, FIDN integer, FIDS integer, LNAM char(16), LNAM_REFS{} char(16), FFPT_RIND{} integer16, EXPSOU integer, NOBJNM char(254), OBJNAM char(254), QUASOU char(254), SOUACC double, TECSOU char(254), VERDAT integer, STATUS char(254), INFORM char(254), NINFOM char(254), NTXTDS char(254), SCAMAX integer, SCAMIN integer, TXTDSC char(254), RECDAT char(254), RECIND char(254), SORDAT char(254), SORIND char(254)
    -> AttributeManager_21
AttributeManager_21
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_soundg_point (writer POSTGIS_1)
2_general_soundg_point (writer POSTGIS_1)
    attributes: fidn varchar(20), expsou varchar(80), nobjnm varchar(80), objnam varchar(80), quasou varchar(80), souacc numeric(24,15), tecsou varchar(80), verdat varchar(80), status varchar(80), inform varchar(80), ninfom varchar(80), ntxtds varchar(80), scamin numeric(24,15), txtdsc varchar(80), sordat varchar(80), sorind varchar(80)
SPRING (reader S57_1)
    attributes: RCID integer, PRIM integer16, GRUP integer16, OBJL integer, RVER integer16, AGEN integer, FIDN integer, FIDS integer, LNAM char(16), LNAM_REFS{} char(16), FFPT_RIND{} integer16, NOBJNM char(254), OBJNAM char(254), INFORM char(254), NINFOM char(254), NTXTDS char(254), SCAMAX integer, SCAMIN integer, TXTDSC char(254), RECDAT char(254), RECIND char(254), SORDAT char(254), SORIND char(254)
    -> AttributeManager_38
AttributeManager_38
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_spring_point (writer POSTGIS_1)
2_general_spring_point (writer POSTGIS_1)
    attributes: fidn varchar(20), nobjnm varchar(80), objnam varchar(80), inform varchar(80), ninfom varchar(80), ntxtds varchar(80), scamin numeric(24,15), txtdsc varchar(80), sordat varchar(80), sorind varchar(80)
TESARE (reader S57_1)
    attributes: RCID integer, PRIM integer16, GRUP integer16, OBJL integer, RVER integer16, AGEN integer, FIDN integer, FIDS integer, LNAM char(16), LNAM_REFS{} char(16), FFPT_RIND{} integer16, NATION char(254), RESTRN char(254), INFORM char(254), NINFOM char(254), NTXTDS char(254), SCAMAX integer, SCAMIN integer, TXTDSC char(254), RECDAT char(254), RECIND char(254), SORDAT char(254), SORIND char(254)
    -> AttributeManager_39
AttributeManager_39
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_tesare_polygon (writer POSTGIS_1)
2_general_tesare_polygon (writer POSTGIS_1)
    attributes: fidn varchar(20), nation varchar(80), restrn varchar(80), inform varchar(80), ninfom varchar(80), ntxtds varchar(80), scamin numeric(24,15), txtdsc varchar(80), sordat varchar(80), sorind varchar(80)
TOPMAR (reader S57_1)
    attributes: RCID integer, PRIM integer16, GRUP integer16, OBJL integer, RVER integer16, AGEN integer, FIDN integer, FIDS integer, LNAM char(16), LNAM_REFS{} char(16), FFPT_RIND{} integer16, COLOUR char(254), COLPAT char(254), DATEND char(254), DATSTA char(254), HEIGHT double, MARSYS integer, STATUS char(254), TOPSHP integer, VERACC double, VERDAT integer, VERLEN double, INFORM char(254), NINFOM char(254), NTXTDS char(254), PICREP char(254), SCAMAX integer, SCAMIN integer, TXTDSC char(254), RECDAT char(254),
      RECIND char(254), SORDAT char(254), SORIND char(254)
    -> AttributeManager_40
AttributeManager_40
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> 2_general_topmar_point (writer POSTGIS_1)
2_general_topmar_point (writer POSTGIS_1)
    attributes: fidn varchar(20), colour varchar(80), colpat varchar(80), datend varchar(80), datsta varchar(80), height numeric(24,15), marsys varchar(80), status varchar(80), topshp varchar(80), veracc numeric(24,15), verdat varchar(80), verlen numeric(24,15), inform varchar(80), ninfom varchar(80), ntxtds varchar(80), picrep varchar(80), scamin numeric(24,15), txtdsc varchar(80), sordat varchar(80), sorind varchar(80)
UWTROC (reader S57_1)
    attributes: RCID integer, PRIM integer16, GRUP integer16, OBJL integer, RVER integer16, AGEN integer, FIDN integer, FIDS integer, LNAM char(16), LNAM_REFS{} char(16), FFPT_RIND{} integer16, EXPSOU integer, NATSUR char(254), NATQUA char(254), NOBJNM char(254), OBJNAM char(254), QUASOU char(254), SOUACC double, STATUS char(254), TECSOU char(254), VALSOU double, VERDAT integer, WATLEV integer, INFORM char(254), NINFOM char(254), NTXTDS char(254), SCAMAX integer, SCAMIN integer, TXTDSC char(254), RECDAT char(254),
      RECIND char(254), SORDAT char(254), SORIND char(254)
    -> AttributeManager_24
AttributeManager_24
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> NullAttributeMapper_6
NullAttributeMapper_6
    ATTRCHOICE = Selected Attributes
    ATTRLIST = VALSOU
    NULL_TREATMENT = Missing
    SOURCE_ATTR_VAL = Empty
    -> 2_general_uwtroc_point (writer POSTGIS_1)
2_general_uwtroc_point (writer POSTGIS_1)
    attributes: fidn varchar(20), expsou varchar(80), natsur varchar(80), natqua varchar(80), nobjnm varchar(80), objnam varchar(80), quasou varchar(80), souacc numeric(24,15), status varchar(80), tecsou varchar(80), valsou numeric(24,15), verdat varchar(80), watlev varchar(80), inform varchar(80), ninfom varchar(80), ntxtds varchar(80), scamin numeric(24,15), txtdsc varchar(80), sordat varchar(80), sorind varchar(80)
VEGATN (reader S57_1)
    attributes: RCID integer, PRIM integer16, GRUP integer16, OBJL integer, RVER integer16, AGEN integer, FIDN integer, FIDS integer, LNAM char(16), LNAM_REFS{} char(16), FFPT_RIND{} integer16, CATVEG char(254), CONVIS integer, ELEVAT double, HEIGHT double, NOBJNM char(254), OBJNAM char(254), VERACC double, VERDAT integer, VERLEN double, INFORM char(254), NINFOM char(254), NTXTDS char(254), SCAMAX integer, SCAMIN integer, TXTDSC char(254), RECDAT char(254), RECIND char(254), SORDAT char(254), SORIND char(254)
    -> AttributeManager_25
AttributeManager_25
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_7
GeometryFilter_7
    BREAK_AGG = No
    GEOM_PORT_NAMES = Point Area
    POINT -> 2_general_vegatn_point (writer POSTGIS_1)
    AREA -> 2_general_vegatn_polygon (writer POSTGIS_1)
2_general_vegatn_point (writer POSTGIS_1)
    attributes: fidn varchar(20), catveg varchar(80), convis varchar(80), elevat numeric(24,15), height numeric(24,15), nobjnm varchar(80), objnam varchar(80), veracc numeric(24,15), verdat varchar(80), verlen numeric(24,15), inform varchar(80), ninfom varchar(80), ntxtds varchar(80), scamin numeric(24,15), txtdsc varchar(80), sordat varchar(80), sorind varchar(80)
2_general_vegatn_polygon (writer POSTGIS_1)
    attributes: fidn varchar(20), catveg varchar(80), convis varchar(80), elevat numeric(24,15), height numeric(24,15), nobjnm varchar(80), objnam varchar(80), veracc numeric(24,15), verdat varchar(80), verlen numeric(24,15), inform varchar(80), ninfom varchar(80), ntxtds varchar(80), scamin numeric(24,15), txtdsc varchar(80), sordat varchar(80), sorind varchar(80)
WATTUR (reader S57_1)
    attributes: RCID integer, PRIM integer16, GRUP integer16, OBJL integer, RVER integer16, AGEN integer, FIDN integer, FIDS integer, LNAM char(16), LNAM_REFS{} char(16), FFPT_RIND{} integer16, CATWAT integer, NOBJNM char(254), OBJNAM char(254), INFORM char(254), NINFOM char(254), NTXTDS char(254), SCAMAX integer, SCAMIN integer, TXTDSC char(254), RECDAT char(254), RECIND char(254), SORDAT char(254), SORIND char(254)
    -> AttributeManager_41
AttributeManager_41
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> GeometryFilter_9
GeometryFilter_9
    BREAK_AGG = No
    GEOM_PORT_NAMES = Point Area
    POINT -> 2_general_wattur_point (writer POSTGIS_1)
    AREA -> 2_general_wattur_polygon (writer POSTGIS_1)
2_general_wattur_point (writer POSTGIS_1)
    attributes: fidn varchar(20), catwat varchar(80), nobjnm varchar(80), objnam varchar(80), inform varchar(80), ninfom varchar(80), ntxtds varchar(80), scamin varchar(80), txtdsc varchar(80), sordat varchar(80), sorind varchar(80)
2_general_wattur_polygon (writer POSTGIS_1)
    attributes: fidn varchar(20), catwat varchar(80), nobjnm varchar(80), objnam varchar(80), inform varchar(80), ninfom varchar(80), ntxtds varchar(80), scamin numeric(24,15), txtdsc varchar(80), sordat varchar(80), sorind varchar(80)
WRECKS (reader S57_1)
    attributes: RCID integer, PRIM integer16, GRUP integer16, OBJL integer, RVER integer16, AGEN integer, FIDN integer, FIDS integer, LNAM char(16), LNAM_REFS{} char(16), FFPT_RIND{} integer16, CATWRK integer, CONRAD integer, CONVIS integer, EXPSOU integer, HEIGHT double, NOBJNM char(254), OBJNAM char(254), QUASOU char(254), SOUACC double, STATUS char(254), TECSOU char(254), VALSOU double, VERACC double, VERDAT integer, VERLEN double, WATLEV integer, INFORM char(254), NINFOM char(254), NTXTDS char(254),
      PICREP char(254), SCAMAX integer, SCAMIN integer, TXTDSC char(254), RECDAT char(254), RECIND char(254), SORDAT char(254), SORIND char(254)
    -> AttributeManager_42
AttributeManager_42
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
    -> NullAttributeMapper_10
NullAttributeMapper_10
    ATTRCHOICE = Selected Attributes
    ATTRLIST = VALSOU
    NULL_TREATMENT = Missing
    SOURCE_ATTR_VAL = Empty
    -> 2_general_wrecks_point (writer POSTGIS_1)
2_general_wrecks_point (writer POSTGIS_1)
    attributes: fidn varchar(20), catwrk varchar(80), conrad varchar(80), convis varchar(80), expsou varchar(80), height numeric(24,10), nobjnm varchar(80), objnam varchar(80), quasou varchar(80), souacc numeric(24,10), status varchar(80), tecsou varchar(80), valsou numeric(24,10), veracc numeric(24,10), verdat varchar(80), verlen numeric(24,10), watlev varchar(80), inform varchar(80), ninfom varchar(80), ntxtds varchar(80), picrep varchar(80), scamin numeric(24,10), txtdsc varchar(80), sordat varchar(80), sorind varchar(80)
