FME workspace 1 Overview.fmw

Parameters:
- DestDataset_POSTGIS = Dev   # Connection
- SourceDataset_S57 = G:\LDS_vector_20210617\1 Overview\*.000   # Source S-57 (ENC) Hydrographic Data File(s)

Readers:
- S57_1: S57 from $(SourceDataset_S57) in LL84-WP

Writers:
- POSTGIS_1: POSTGIS to $(DestDataset_POSTGIS)

BUAARE (reader S57_1)
    attributes: RCID integer, PRIM integer16, GRUP integer16, OBJL integer, RVER integer16, AGEN integer, FIDN integer, FIDS integer, LNAM char(16), LNAM_REFS{} char(16), FFPT_RIND{} integer16, CATBUA integer, CONDTN integer, CONRAD integer, CONVIS integer, HEIGHT double, NOBJNM char(254), OBJNAM char(254), VERACC double, VERDAT integer, INFORM char(254), NINFOM char(254), NTXTDS char(254), PICREP char(254), SCAMAX integer, SCAMIN integer, TXTDSC char(254), RECDAT char(254), RECIND char(254), SORDAT char(254),
      SORIND char(254)
    -> AttributeManager
AttributeManager
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE PICREP
      REMOVE SCAMAX
      REMOVE RECDAT
      REMOVE RECIND
      REMOVE s57_update_file{}
      REMOVE s57_update_type{}
      REMOVE DSNM
    -> GeometryFilter_2
GeometryFilter_2
    BREAK_AGG = No
    GEOM_PORT_NAMES = Point Area
    POINT -> 1_overview_buaare_point (writer POSTGIS_1)
1_overview_buaare_point (writer POSTGIS_1)
    attributes: fidn varchar(20), catbua varchar(80), condtn varchar(80), conrad varchar(80), convis varchar(80), height numeric(24,15), nobjnm varchar(80), objnam varchar(80), veracc numeric(24,15), verdat varchar(80), inform varchar(80), ninfom varchar(80), ntxtds varchar(80), scamin numeric(24,15), txtdsc varchar(80), sordat varchar(80), sorind varchar(80)
CBLSUB (reader S57_1)
    attributes: RCID integer, PRIM integer16, GRUP integer16, OBJL integer, RVER integer16, AGEN integer, FIDN integer, FIDS integer, LNAM char(16), LNAM_REFS{} char(16), FFPT_RIND{} integer16, BURDEP double, CATCBL integer, CONDTN integer, DATEND char(254), DATSTA char(254), NOBJNM char(254), OBJNAM char(254), STATUS char(254), VERDAT integer, INFORM char(254), NINFOM char(254), NTXTDS char(254), SCAMAX integer, SCAMIN integer, TXTDSC char(254), RECDAT char(254), RECIND char(254), SORDAT char(254), SORIND char(254)
    -> AttributeManager_2
AttributeManager_2
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_cblsub_arc (writer POSTGIS_1)
1_overview_cblsub_arc (writer POSTGIS_1)
    attributes: fidn varchar(20), burdep numeric(24,15), catcbl varchar(80), condtn varchar(80), datend varchar(80), datsta varchar(80), nobjnm varchar(80), objnam varchar(80), status varchar(80), verdat varchar(80), inform varchar(80), ninfom varchar(80), ntxtds varchar(80), scamin numeric(24,15), txtdsc varchar(80), sordat varchar(80), sorind varchar(80)
COALNE (reader S57_1)
    attributes: RCID integer, PRIM integer16, GRUP integer16, OBJL integer, RVER integer16, AGEN integer, FIDN integer, FIDS integer, LNAM char(16), LNAM_REFS{} char(16), FFPT_RIND{} integer16, CATCOA integer, COLOUR char(254), CONRAD integer, CONVIS integer, ELEVAT double, NOBJNM char(254), OBJNAM char(254), VERACC double, VERDAT integer, INFORM char(254), NINFOM char(254), NTXTDS char(254), PICREP char(254), SCAMAX integer, SCAMIN integer, TXTDSC char(254), RECDAT char(254), RECIND char(254), SORDAT char(254),
      SORIND char(254)
    -> AttributeManager_3
AttributeManager_3
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_coalne_arc (writer POSTGIS_1)
1_overview_coalne_arc (writer POSTGIS_1)
    attributes: fidn varchar(20), catcoa varchar(80), colour varchar(80), conrad varchar(80), convis varchar(80), elevat numeric(24,15), nobjnm varchar(80), objnam varchar(80), veracc numeric(24,15), verdat varchar(80), inform varchar(80), ninfom varchar(80), ntxtds varchar(80), picrep varchar(80), scamin numeric(24,15), txtdsc varchar(80), sordat varchar(80), sorind varchar(80)
CURENT (reader S57_1)
    attributes: RCID integer, PRIM integer16, GRUP integer16, OBJL integer, RVER integer16, AGEN integer, FIDN integer, FIDS integer, LNAM char(16), LNAM_REFS{} char(16), FFPT_RIND{} integer16, CURVEL double, DATEND char(254), DATSTA char(254), NOBJNM char(254), OBJNAM char(254), ORIENT double, PEREND char(254), PERSTA char(254), INFORM char(254), NINFOM char(254), SCAMAX integer, SCAMIN integer, RECDAT char(254), RECIND char(254), SORDAT char(254), SORIND char(254)
    -> AttributeManager_4
AttributeManager_4
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_curent_point (writer POSTGIS_1)
1_overview_curent_point (writer POSTGIS_1)
    attributes: fidn varchar(20), curvel varchar(80), datend varchar(80), datsta varchar(80), nobjnm varchar(80), objnam varchar(80), orient numeric(24,15), perend varchar(80), persta varchar(80), inform varchar(80), ninfom varchar(80), scamin numeric(24,15), sordat varchar(80), sorind varchar(80)
DAYMAR (reader S57_1)
    attributes: RCID integer, PRIM integer16, GRUP integer16, OBJL integer, RVER integer16, AGEN integer, FIDN integer, FIDS integer, LNAM char(16), LNAM_REFS{} char(16), FFPT_RIND{} integer16, CATSPM char(254), COLOUR char(254), COLPAT char(254), DATEND char(254), DATSTA char(254), ELEVAT double, HEIGHT double, NATCON char(254), NOBJNM char(254), OBJNAM char(254), PEREND char(254), PERSTA char(254), STATUS char(254), TOPSHP integer, VERACC double, VERDAT integer, VERLEN double, INFORM char(254), NINFOM char(254),
      NTXTDS char(254), SCAMAX integer, SCAMIN integer, TXTDSC char(254), RECDAT char(254), RECIND char(254), SORDAT char(254), SORIND char(254)
    -> AttributeManager_5
AttributeManager_5
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> NullAttributeMapper_2
NullAttributeMapper_2
    ATTRCHOICE = Selected Attributes
    ATTRLIST = TOPSHP
    NULL_TREATMENT = Missing
    SOURCE_ATTR_VAL = Empty
    -> 1_overview_daymar_point (writer POSTGIS_1)
1_overview_daymar_point (writer POSTGIS_1)
    attributes: fidn varchar(20), catspm varchar(80), colour varchar(80), colpat varchar(80), datend varchar(80), datsta varchar(80), elevat numeric(24,15), height numeric(24,15), natcon varchar(80), nobjnm varchar(80), objnam varchar(80), perend varchar(80), persta varchar(80), status varchar(80), topshp varchar(80), veracc numeric(24,15), verdat varchar(80), verlen numeric(24,15), inform varchar(80), ninfom varchar(80), ntxtds varchar(80), scamin numeric(24,15), txtdsc varchar(80), sordat varchar(80), sorind varchar(80)
DEPARE (reader S57_1)
    attributes: RCID integer, PRIM integer16, GRUP integer16, OBJL integer, RVER integer16, AGEN integer, FIDN integer, FIDS integer, LNAM char(16), LNAM_REFS{} char(16), FFPT_RIND{} integer16, DRVAL1 double, DRVAL2 double, QUASOU char(254), SOUACC double, VERDAT integer, INFORM char(254), NINFOM char(254), NTXTDS char(254), SCAMAX integer, SCAMIN integer, TXTDSC char(254), RECDAT char(254), RECIND char(254), SORDAT char(254), SORIND char(254)
    -> AttributeManager_6
AttributeManager_6
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> NullAttributeMapper
NullAttributeMapper
    ATTRCHOICE = Selected Attributes
    ATTRLIST = DRVAL1
    NULL_TREATMENT = Missing
    SOURCE_ATTR_VAL = Empty
    -> 1_overview_depare_polygon (writer POSTGIS_1)
1_overview_depare_polygon (writer POSTGIS_1)
    attributes: fidn varchar(20), drval1 numeric(24,15), drval2 numeric(24,15), quasou varchar(80), souacc numeric(24,15), verdat varchar(80), inform varchar(80), ninfom varchar(80), ntxtds varchar(80), scamin numeric(24,15), txtdsc varchar(80), sordat varchar(80), sorind varchar(80)
DEPCNT (reader S57_1)
    attributes: RCID integer, PRIM integer16, GRUP integer16, OBJL integer, RVER integer16, AGEN integer, FIDN integer, FIDS integer, LNAM char(16), LNAM_REFS{} char(16), FFPT_RIND{} integer16, VALDCO double, VERDAT integer, INFORM char(254), NINFOM char(254), NTXTDS char(254), SCAMAX integer, SCAMIN integer, TXTDSC char(254), RECDAT char(254), RECIND char(254), SORDAT char(254), SORIND char(254)
    -> AttributeManager_7
AttributeManager_7
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
      SET_TO HYPCAT
    -> 1_overview_depcnt_arc (writer POSTGIS_1)
1_overview_depcnt_arc (writer POSTGIS_1)
    attributes: fidn varchar(20), valdco numeric(24,15), verdat varchar(80), inform varchar(80), ninfom varchar(80), ntxtds varchar(80), scamin numeric(24,15), txtdsc varchar(80), sordat varchar(80), sorind varchar(80), hypcat varchar(80)
DSID (reader S57_1)
    attributes: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
EXEZNE (reader S57_1)
    attributes: RCID integer, PRIM integer16, GRUP integer16, OBJL integer, RVER integer16, AGEN integer, FIDN integer, FIDS integer, LNAM char(16), LNAM_REFS{} char(16), FFPT_RIND{} integer16, NATION char(254), INFORM char(254), NINFOM char(254), NTXTDS char(254), SCAMAX integer, SCAMIN integer, TXTDSC char(254), RECDAT char(254), RECIND char(254), SORDAT char(254), SORIND char(254)
    -> AttributeManager_8
AttributeManager_8
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_exezne_polygon (writer POSTGIS_1)
1_overview_exezne_polygon (writer POSTGIS_1)
    attributes: fidn varchar(20), nation varchar(80), inform varchar(80), ninfom varchar(80), ntxtds varchar(80), scamin numeric(24,15), txtdsc varchar(80), sordat varchar(80), sorind varchar(80)
Generic (reader S57_1)
    attributes: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
LIGHTS (reader S57_1)
    attributes: RCID integer, PRIM integer16, GRUP integer16, OBJL integer, RVER integer16, AGEN integer, FIDN integer, FIDS integer, LNAM char(16), LNAM_REFS{} char(16), FFPT_RIND{} integer16, CATLIT char(254), COLOUR char(254), DATEND char(254), DATSTA char(254), EXCLIT integer, HEIGHT double, LITCHR integer, LITVIS char(254), MARSYS integer, MLTYLT integer, NOBJNM char(254), OBJNAM char(254), ORIENT double, PEREND char(254), PERSTA char(254), SECTR1 double, SECTR2 double, SIGGRP char(254), SIGPER double,
      SIGSEQ char(254), STATUS char(254), VERACC double, VALNMR double, VERDAT integer, INFORM char(254), NINFOM char(254), NTXTDS char(254), SCAMAX integer, SCAMIN integer, TXTDSC char(254), RECDAT char(254), RECIND char(254), SORDAT char(254), SORIND char(254)
    -> AttributeManager_9
AttributeManager_9
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_lights_point (writer POSTGIS_1)
1_overview_lights_point (writer POSTGIS_1)
    attributes: fidn varchar(20), catlit varchar(80), colour varchar(80), datend varchar(80), datsta varchar(80), exclit varchar(80), height numeric(24,15), litchr varchar(80), litvis varchar(80), marsys varchar(80), mltylt numeric(24,15), nobjnm varchar(80), objnam varchar(80), orient numeric(24,15), perend varchar(80), persta varchar(80), sectr1 numeric(24,15), sectr2 numeric(24,15), siggrp varchar(80), sigper varchar(80), sigseq varchar(80), status varchar(80), veracc numeric(24,15), valnmr numeric(24,15), verdat varchar(80), inform varchar(256), ninfom varchar(80), ntxtds varchar(80), scamin numeric(24,15), txtdsc varchar(80),
      sordat varchar(80), sorind varchar(80)
LNDARE (reader S57_1)
    attributes: RCID integer, PRIM integer16, GRUP integer16, OBJL integer, RVER integer16, AGEN integer, FIDN integer, FIDS integer, LNAM char(16), LNAM_REFS{} char(16), FFPT_RIND{} integer16, CONDTN integer, NOBJNM char(254), OBJNAM char(254), STATUS char(254), INFORM char(254), NINFOM char(254), NTXTDS char(254), SCAMAX integer, SCAMIN integer, TXTDSC char(254), RECDAT char(254), RECIND char(254), SORDAT char(254), SORIND char(254)
    -> AttributeManager_10
AttributeManager_10
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> GeometryFilter
GeometryFilter
    BREAK_AGG = No
    GEOM_PORT_NAMES = Point Area
    POINT -> 1_overview_lndare_point (writer POSTGIS_1)
    AREA -> 1_overview_lndare_polygon (writer POSTGIS_1)
1_overview_lndare_point (writer POSTGIS_1)
    attributes: fidn varchar(20), condtn varchar(80), nobjnm varchar(80), objnam varchar(80), status varchar(80), inform varchar(80), ninfom varchar(80), ntxtds varchar(80), scamin numeric(24,15), txtdsc varchar(80), sordat varchar(80), sorind varchar(80)
1_overview_lndare_polygon (writer POSTGIS_1)
    attributes: fidn varchar(20), condtn varchar(80), nobjnm varchar(80), objnam varchar(80), status varchar(80), inform varchar(80), ninfom varchar(80), ntxtds varchar(80), scamin numeric(24,15), txtdsc varchar(80), sordat varchar(80), sorind varchar(80)
LNDELV (reader S57_1)
    attributes: RCID integer, PRIM integer16, GRUP integer16, OBJL integer, RVER integer16, AGEN integer, FIDN integer, FIDS integer, LNAM char(16), LNAM_REFS{} char(16), FFPT_RIND{} integer16, CONVIS integer, ELEVAT double, NOBJNM char(254), OBJNAM char(254), VERACC double, VERDAT integer, INFORM char(254), NINFOM char(254), NTXTDS char(254), SCAMAX integer, SCAMIN integer, TXTDSC char(254), RECDAT char(254), RECIND char(254), SORDAT char(254), SORIND char(254)
    -> AttributeManager_12
AttributeManager_12
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_lndelv_point (writer POSTGIS_1)
1_overview_lndelv_point (writer POSTGIS_1)
    attributes: fidn varchar(20), convis varchar(80), elevat numeric(24,15), nobjnm varchar(80), objnam varchar(80), veracc numeric(24,15), verdat varchar(80), inform varchar(80), ninfom varchar(80), ntxtds varchar(80), scamin numeric(24,15), txtdsc varchar(80), sordat varchar(80), sorind varchar(80)
LNDMRK (reader S57_1)
    attributes: RCID integer, PRIM integer16, GRUP integer16, OBJL integer, RVER integer16, AGEN integer, FIDN integer, FIDS integer, LNAM char(16), LNAM_REFS{} char(16), FFPT_RIND{} integer16, CATLMK char(254), COLOUR char(254), COLPAT char(254), CONDTN integer, CONRAD integer, CONVIS integer, ELEVAT double, FUNCTN char(254), HEIGHT double, NATCON char(254), NOBJNM char(254), OBJNAM char(254), STATUS char(254), VERACC double, VERDAT integer, VERLEN double, INFORM char(254), NINFOM char(254), NTXTDS char(254),
      PICREP char(254), SCAMAX integer, SCAMIN integer, TXTDSC char(254), RECDAT char(254), RECIND char(254), SORDAT char(254), SORIND char(254)
    -> AttributeManager_13
AttributeManager_13
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE PICREP
      REMOVE SCAMAX
      REMOVE RECDAT
      REMOVE RECIND
      REMOVE s57_update_file{}
      REMOVE s57_update_type{}
      REMOVE DSNM
    -> NullAttributeMapper_3
NullAttributeMapper_3
    ATTRCHOICE = Selected Attributes
    ATTRLIST = CONVIS
    NULL_TREATMENT = Missing
    SOURCE_ATTR_VAL = Empty
    -> 1_overview_lndmrk_point (writer POSTGIS_1)
1_overview_lndmrk_point (writer POSTGIS_1)
    attributes: fidn varchar(20), catlmk varchar(80), colour varchar(80), colpat varchar(80), condtn varchar(80), conrad varchar(80), convis varchar(80), elevat numeric(24,15), functn varchar(80), height numeric(24,15), natcon varchar(80), nobjnm varchar(80), objnam varchar(80), status varchar(80), veracc numeric(24,15), verdat varchar(80), verlen numeric(24,15), inform varchar(256), ninfom varchar(80), ntxtds varchar(80), scamin numeric(24,15), txtdsc varchar(80), sordat varchar(80), sorind varchar(80)
LNDRGN (reader S57_1)
    attributes: RCID integer, PRIM integer16, GRUP integer16, OBJL integer, RVER integer16, AGEN integer, FIDN integer, FIDS integer, LNAM char(16), LNAM_REFS{} char(16), FFPT_RIND{} integer16, CATLND char(254), NATQUA char(254), NATSUR char(254), NOBJNM char(254), OBJNAM char(254), WATLEV integer, INFORM char(254), NINFOM char(254), NTXTDS char(254), SCAMAX integer, SCAMIN integer, TXTDSC char(254), RECDAT char(254), RECIND char(254), SORDAT char(254), SORIND char(254)
    -> AttributeManager_14
AttributeManager_14
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> GeometryFilter_3
GeometryFilter_3
    BREAK_AGG = No
    GEOM_PORT_NAMES = Point Area
    POINT -> 1_overview_lndrgn_point (writer POSTGIS_1)
1_overview_lndrgn_point (writer POSTGIS_1)
    attributes: fidn varchar(20), catlnd varchar(80), natqua varchar(80), natsur varchar(80), nobjnm varchar(80), objnam varchar(80), watlev varchar(80), inform varchar(80), ninfom varchar(80), ntxtds varchar(80), scamin numeric(24,15), txtdsc varchar(80), sordat varchar(80), sorind varchar(80)
M_COVR (reader S57_1)
    attributes: RCID integer, PRIM integer16, GRUP integer16, OBJL integer, RVER integer16, AGEN integer, FIDN integer, FIDS integer, LNAM char(16), LNAM_REFS{} char(16), FFPT_RIND{} integer16, CATCOV integer, INFORM char(254), NINFOM char(254), RECDAT char(254), RECIND char(254), SORDAT char(254), SORIND char(254)
    -> AttributeManager_15
AttributeManager_15
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
      REMOVE s57_update_file{}
      REMOVE s57_update_type{}
      REMOVE DSNM
    -> 1_overview_m_covr_polygon (writer POSTGIS_1)
1_overview_m_covr_polygon (writer POSTGIS_1)
    attributes: fidn varchar(20), catcov varchar(80), inform varchar(80), ninfom varchar(80), sordat varchar(80), sorind varchar(80)
M_NPUB (reader S57_1)
    attributes: RCID integer, PRIM integer16, GRUP integer16, OBJL integer, RVER integer16, AGEN integer, FIDN integer, FIDS integer, LNAM char(16), LNAM_REFS{} char(16), FFPT_RIND{} integer16, INFORM char(254), NINFOM char(254), NTXTDS char(254), PICREP char(254), PUBREF char(254), TXTDSC char(254), RECDAT char(254), RECIND char(254), SORDAT char(254), SORIND char(254)
    -> AttributeManager_16
AttributeManager_16
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
      REMOVE s57_update_file{}
      REMOVE s57_update_type{}
      REMOVE DSNM
    -> 1_overview_m_npub_polygon (writer POSTGIS_1)
1_overview_m_npub_polygon (writer POSTGIS_1)
    attributes: fidn varchar(20), inform varchar(80), ninfom varchar(80), ntxtds varchar(80), picrep varchar(80), pubref varchar(80), txtdsc varchar(80), sordat varchar(80), sorind varchar(80)
M_NSYS (reader S57_1)
    attributes: RCID integer, PRIM integer16, GRUP integer16, OBJL integer, RVER integer16, AGEN integer, FIDN integer, FIDS integer, LNAM char(16), LNAM_REFS{} char(16), FFPT_RIND{} integer16, MARSYS integer, ORIENT double, INFORM char(254), NINFOM char(254), NTXTDS char(254), SCAMAX integer, SCAMIN integer, TXTDSC char(254), RECDAT char(254), RECIND char(254), SORDAT char(254), SORIND char(254)
    -> AttributeManager_17
AttributeManager_17
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_m_nsys_polygon (writer POSTGIS_1)
1_overview_m_nsys_polygon (writer POSTGIS_1)
    attributes: fidn varchar(20), marsys varchar(80), orient numeric(24,15), inform varchar(80), ninfom varchar(80), ntxtds varchar(80), scamin numeric(24,15), txtdsc varchar(80), sordat varchar(80), sorind varchar(80)
M_QUAL (reader S57_1)
    attributes: RCID integer, PRIM integer16, GRUP integer16, OBJL integer, RVER integer16, AGEN integer, FIDN integer, FIDS integer, LNAM char(16), LNAM_REFS{} char(16), FFPT_RIND{} integer16, CATQUA integer, CATZOC integer, DRVAL1 double, DRVAL2 double, POSACC double, SOUACC double, SUREND char(254), SURSTA char(254), TECSOU char(254), VERDAT integer, INFORM char(254), NINFOM char(254), NTXTDS char(254), TXTDSC char(254), RECDAT char(254), RECIND char(254), SORDAT char(254), SORIND char(254)
    -> AttributeManager_18
AttributeManager_18
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE RECDAT
      REMOVE RECIND
      REMOVE s57_update_file{}
      REMOVE s57_update_type{}
      REMOVE DSNM
    -> 1_overview_m_qual_polygon (writer POSTGIS_1)
1_overview_m_qual_polygon (writer POSTGIS_1)
    attributes: fidn varchar(20), catqua varchar(80), catzoc varchar(80), drval1 numeric(24,15), drval2 numeric(24,15), posacc numeric(24,15), souacc numeric(24,15), surend varchar(80), sursta varchar(80), tecsou varchar(80), verdat varchar(80), inform varchar(80), ninfom varchar(80), ntxtds varchar(80), txtdsc varchar(80), sordat varchar(80), sorind varchar(80)
MAGVAR (reader S57_1)
    attributes: RCID integer, PRIM integer16, GRUP integer16, OBJL integer, RVER integer16, AGEN integer, FIDN integer, FIDS integer, LNAM char(16), LNAM_REFS{} char(16), FFPT_RIND{} integer16, DATEND char(254), DATSTA char(254), RYRMGV char(254), VALACM double, VALMAG double, INFORM char(254), NINFOM char(254), SCAMAX integer, SCAMIN integer, RECDAT char(254), RECIND char(254), SORDAT char(254), SORIND char(254)
    -> AttributeManager_19
AttributeManager_19
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_magvar_arc (writer POSTGIS_1)
1_overview_magvar_arc (writer POSTGIS_1)
    attributes: fidn varchar(20), datend varchar(80), datsta varchar(80), ryrmgv varchar(80), valacm numeric(24,15), valmag numeric(24,15), inform varchar(80), ninfom varchar(80), scamin numeric(24,15), sordat varchar(80), sorind varchar(80)
OBSTRN (reader S57_1)
    attributes: RCID integer, PRIM integer16, GRUP integer16, OBJL integer, RVER integer16, AGEN integer, FIDN integer, FIDS integer, LNAM char(16), LNAM_REFS{} char(16), FFPT_RIND{} integer16, CATOBS integer, CONDTN integer, EXPSOU integer, HEIGHT double, NATCON char(254), NATQUA char(254), NOBJNM char(254), OBJNAM char(254), PRODCT char(254), QUASOU char(254), SOUACC double, STATUS char(254), TECSOU char(254), VALSOU double, VERACC double, VERDAT integer, VERLEN double, WATLEV integer, NATSUR char(254),
      INFORM char(254), NINFOM char(254), NTXTDS char(254), SCAMAX integer, SCAMIN integer, TXTDSC char(254), RECDAT char(254), RECIND char(254), SORDAT char(254), SORIND char(254)
    -> AttributeManager_20
AttributeManager_20
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> GeometryFilter_4
GeometryFilter_4
    BREAK_AGG = No
    GEOM_PORT_NAMES = Point Area
    POINT -> NullAttributeMapper_5
    AREA -> NullAttributeMapper_4
NullAttributeMapper_5
    ATTRCHOICE = Selected Attributes
    ATTRLIST = VALSOU
    NULL_TREATMENT = Missing
    SOURCE_ATTR_VAL = Empty
    -> 1_overview_obstrn_point (writer POSTGIS_1)
1_overview_obstrn_point (writer POSTGIS_1)
    attributes: fidn varchar(20), catobs varchar(80), condtn varchar(80), expsou varchar(80), height numeric(24,15), natcon varchar(80), natqua varchar(80), nobjnm varchar(80), objnam varchar(80), prodct varchar(80), quasou varchar(80), souacc numeric(24,15), status varchar(80), tecsou varchar(80), valsou numeric(24,15), veracc numeric(24,15), verdat varchar(80), verlen numeric(24,15), watlev varchar(80), natsur varchar(80), inform varchar(80), ninfom varchar(80), ntxtds varchar(80), scamin numeric(24,15), txtdsc varchar(80), sordat varchar(80), sorind varchar(80)
NullAttributeMapper_4
    ATTRCHOICE = Selected Attributes
    ATTRLIST = VALSOU
    NULL_TREATMENT = Missing
    SOURCE_ATTR_VAL = Empty
    -> 1_overview_obstrn_polygon (writer POSTGIS_1)
1_overview_obstrn_polygon (writer POSTGIS_1)
    attributes: fidn varchar(20), catobs varchar(80), condtn varchar(80), expsou varchar(80), height numeric(24,15), natcon varchar(80), natqua varchar(80), nobjnm varchar(80), objnam varchar(80), prodct varchar(80), quasou varchar(80), souacc numeric(24,15), status varchar(80), tecsou varchar(80), valsou numeric(24,15), veracc numeric(24,15), verdat varchar(80), verlen numeric(24,15), watlev varchar(80), natsur varchar(80), inform varchar(80), ninfom varchar(80), ntxtds varchar(80), scamin numeric(24,15), txtdsc varchar(80), sordat varchar(80), sorind varchar(80)
RDOSTA (reader S57_1)
    attributes: RCID integer, PRIM integer16, GRUP integer16, OBJL integer, RVER integer16, AGEN integer, FIDN integer, FIDS integer, LNAM char(16), LNAM_REFS{} char(16), FFPT_RIND{} integer16, CALSGN char(254), CATROS char(254), COMCHA char(254), DATEND char(254), DATSTA char(254), ESTRNG double, NOBJNM char(254), OBJNAM char(254), ORIENT double, PEREND char(254), PERSTA char(254), SIGFRQ integer, STATUS char(254), INFORM char(254), NINFOM char(254), NTXTDS char(254), SCAMAX integer, SCAMIN integer, TXTDSC char(254),
      RECDAT char(254), RECIND char(254), SORDAT char(254), SORIND char(254)
    -> AttributeManager_22
AttributeManager_22
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_rdosta_point (writer POSTGIS_1)
1_overview_rdosta_point (writer POSTGIS_1)
    attributes: fidn varchar(20), calsgn varchar(80), catros varchar(80), comcha varchar(80), datend varchar(80), datsta varchar(80), estrng numeric(24,15), nobjnm varchar(80), objnam varchar(80), orient numeric(24,15), perend varchar(80), persta varchar(80), sigfrq numeric(24,15), status varchar(80), inform varchar(80), ninfom varchar(80), ntxtds varchar(80), scamin numeric(24,15), txtdsc varchar(80), sordat varchar(80), sorind varchar(80)
SBDARE (reader S57_1)
    attributes: RCID integer, PRIM integer16, GRUP integer16, OBJL integer, RVER integer16, AGEN integer, FIDN integer, FIDS integer, LNAM char(16), LNAM_REFS{} char(16), FFPT_RIND{} integer16, COLOUR char(254), NATQUA char(254), NATSUR char(254), WATLEV integer, OBJNAM char(254), NOBJNM char(254), INFORM char(254), NINFOM char(254), NTXTDS char(254), SCAMAX integer, SCAMIN integer, TXTDSC char(254), RECDAT char(254), RECIND char(254), SORDAT char(254), SORIND char(254)
    -> AttributeManager_23
AttributeManager_23
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> GeometryFilter_5
GeometryFilter_5
    BREAK_AGG = No
    GEOM_PORT_NAMES = Point Area
    POINT -> 1_overview_sbdare_point (writer POSTGIS_1)
    AREA -> 1_overview_sbdare_polygon (writer POSTGIS_1)
1_overview_sbdare_point (writer POSTGIS_1)
    attributes: fidn varchar(20), colour varchar(80), natqua varchar(80), natsur varchar(80), watlev varchar(80), objnam varchar(80), nobjnm varchar(80), inform varchar(80), ninfom varchar(80), ntxtds varchar(80), scamin numeric(24,15), txtdsc varchar(80), sordat varchar(80), sorind varchar(80)
1_overview_sbdare_polygon (writer POSTGIS_1)
    attributes: fidn varchar(20), colour varchar(80), natqua varchar(80), natsur varchar(80), watlev varchar(80), objnam varchar(80), nobjnm varchar(80), inform varchar(80), ninfom varchar(80), ntxtds varchar(80), scamin numeric(24,15), txtdsc varchar(80), sordat varchar(80), sorind varchar(80)
SEAARE (reader S57_1)
    attributes: RCID integer, PRIM integer16, GRUP integer16, OBJL integer, RVER integer16, AGEN integer, FIDN integer, FIDS integer, LNAM char(16), LNAM_REFS{} char(16), FFPT_RIND{} integer16, CATSEA integer, NOBJNM char(254), OBJNAM char(254), INFORM char(254), NINFOM char(254), NTXTDS char(254), SCAMAX integer, SCAMIN integer, TXTDSC char(254), RECDAT char(254), RECIND char(254), SORDAT char(254), SORIND char(254)
    -> AttributeManager_11
AttributeManager_11
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> GeometryFilter_6
GeometryFilter_6
    BREAK_AGG = No
    GEOM_PORT_NAMES = Point Area
    POINT -> 1_overview_seaare_point (writer POSTGIS_1)
    AREA -> 1_overview_seaare_polygon (writer POSTGIS_1)
1_overview_seaare_point (writer POSTGIS_1)
    attributes: fidn varchar(20), catsea varchar(80), nobjnm varchar(80), objnam varchar(80), inform varchar(80), ninfom varchar(80), ntxtds varchar(80), scamin numeric(24,15), txtdsc varchar(80), sordat varchar(80), sorind varchar(80)
1_overview_seaare_polygon (writer POSTGIS_1)
    attributes: fidn varchar(20), catsea varchar(80), nobjnm varchar(80), objnam varchar(80), inform varchar(80), ninfom varchar(80), ntxtds varchar(80), scamin numeric(24,15), txtdsc varchar(80), sordat varchar(80), sorind varchar(80)
SOUNDG (reader S57_1)
    attributes: RCID integer, PRIM integer16, GRUP integer16, OBJL integer, RVER integer16, AGEN integer, FIDN integer, FIDS integer, LNAM char(16), LNAM_REFS{} char(16), FFPT_RIND{} integer16, EXPSOU integer, NOBJNM char(254), OBJNAM char(254), QUASOU char(254), SOUACC double, TECSOU char(254), VERDAT integer, STATUS char(254), INFORM char(254), NINFOM char(254), NTXTDS char(254), SCAMAX integer, SCAMIN integer, TXTDSC char(254), RECDAT char(254), RECIND char(254), SORDAT char(254), SORIND char(254)
    -> AttributeManager_21
AttributeManager_21
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> 1_overview_soundg_point (writer POSTGIS_1)
1_overview_soundg_point (writer POSTGIS_1)
    attributes: fidn varchar(20), expsou varchar(80), nobjnm varchar(80), objnam varchar(80), quasou varchar(80), souacc numeric(24,15), tecsou varchar(80), verdat varchar(80), status varchar(80), inform varchar(80), ninfom varchar(80), ntxtds varchar(80), scamin numeric(24,15), txtdsc varchar(80), sordat varchar(80), sorind varchar(80)
UWTROC (reader S57_1)
    attributes: RCID integer, PRIM integer16, GRUP integer16, OBJL integer, RVER integer16, AGEN integer, FIDN integer, FIDS integer, LNAM char(16), LNAM_REFS{} char(16), FFPT_RIND{} integer16, EXPSOU integer, NATSUR char(254), NATQUA char(254), NOBJNM char(254), OBJNAM char(254), QUASOU char(254), SOUACC double, STATUS char(254), TECSOU char(254), VALSOU double, VERDAT integer, WATLEV integer, INFORM char(254), NINFOM char(254), NTXTDS char(254), SCAMAX integer, SCAMIN integer, TXTDSC char(254), RECDAT char(254),
      RECIND char(254), SORDAT char(254), SORIND char(254)
    -> AttributeManager_24
AttributeManager_24
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> NullAttributeMapper_6
NullAttributeMapper_6
    ATTRCHOICE = Selected Attributes
    ATTRLIST = VALSOU
    NULL_TREATMENT = Missing
    SOURCE_ATTR_VAL = Empty
    -> 1_overview_uwtroc_point (writer POSTGIS_1)
1_overview_uwtroc_point (writer POSTGIS_1)
    attributes: fidn varchar(20), expsou varchar(80), natsur varchar(80), natqua varchar(80), nobjnm varchar(80), objnam varchar(80), quasou varchar(80), souacc numeric(24,15), status varchar(80), tecsou varchar(80), valsou numeric(24,15), verdat varchar(80), watlev varchar(80), inform varchar(80), ninfom varchar(80), ntxtds varchar(80), scamin numeric(24,15), txtdsc varchar(80), sordat varchar(80), sorind varchar(80)
VEGATN (reader S57_1)
    attributes: RCID integer, PRIM integer16, GRUP integer16, OBJL integer, RVER integer16, AGEN integer, FIDN integer, FIDS integer, LNAM char(16), LNAM_REFS{} char(16), FFPT_RIND{} integer16, CATVEG char(254), CONVIS integer, ELEVAT double, HEIGHT double, NOBJNM char(254), OBJNAM char(254), VERACC double, VERDAT integer, VERLEN double, INFORM char(254), NINFOM char(254), NTXTDS char(254), SCAMAX integer, SCAMIN integer, TXTDSC char(254), RECDAT char(254), RECIND char(254), SORDAT char(254), SORIND char(254)
    -> AttributeManager_25
AttributeManager_25
    ATTR_TABLE:
      REMOVE RCID
      REMOVE PRIM
      REMOVE GRUP
      REMOVE OBJL
      REMOVE RVER
      REMOVE AGEN
      REMOVE FIDS
      REMOVE LNAM
      REMOVE LNAM_REFS{}
      REMOVE FFPT_RIND{}
      REMOVE SCAMAX
      REMOVE RECDAT
      REMOVE RECIND
      REMOVE s57_update_file{}
      REMOVE s57_update_type{}
      REMOVE DSNM
    -> GeometryFilter_7
GeometryFilter_7
    BREAK_AGG = No
    GEOM_PORT_NAMES = Point Area
    POINT -> 1_overview_vegatn_point (writer POSTGIS_1)
    AREA -> 1_overview_vegatn_polygon (writer POSTGIS_1)
1_overview_vegatn_point (writer POSTGIS_1)
    attributes: fidn varchar(20), catveg varchar(80), convis varchar(80), elevat numeric(24,15), height numeric(24,15), nobjnm varchar(80), objnam varchar(80), veracc numeric(24,15), verdat varchar(80), verlen numeric(24,15), inform varchar(80), ninfom varchar(80), ntxtds varchar(80), scamin numeric(24,15), txtdsc varchar(80), sordat varchar(80), sorind varchar(80)
1_overview_vegatn_polygon (writer POSTGIS_1)
    attributes: fidn varchar(20), catveg varchar(80), convis varchar(80), elevat numeric(24,15), height numeric(24,15), nobjnm varchar(80), objnam varchar(80), veracc numeric(24,15), verdat varchar(80), verlen numeric(24,15), inform varchar(80), ninfom varchar(80), ntxtds varchar(80), scamin numeric(24,15), txtdsc varchar(80), sordat varchar(80), sorind varchar(80)
